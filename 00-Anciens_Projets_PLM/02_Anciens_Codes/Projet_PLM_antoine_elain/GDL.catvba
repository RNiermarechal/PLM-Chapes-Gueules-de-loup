Attribute VB_Name = "Feuille_saisie"
Attribute VB_Base = "0{8605B0F1-DD09-4C05-9F5D-E114D5D40B39}{15E6062D-A014-43A4-AC2B-BE547B79FF61}"
Attribute VB_GlobalNameSpace = False
Attribute VB_Creatable = False
Attribute VB_PredeclaredId = True
Attribute VB_Exposed = False
Attribute VB_TemplateDerived = False
Attribute VB_Customizable = False


Private Sub Bouton_ok_Click()
creation = "oui"
Dimension = ComboBox1.Value
Feuille_saisie.Hide
End Sub
Private Sub Bouton_annuler_Click()
creation = "non"
fin = True
Feuille_saisie.Hide
End Sub


Private Sub CommandButton1_Click()
Feuille_saisie.Hide

Dim Usel As Selection
Dim UselLB As Object
Dim InputObject(0)
Dim oStatus As String
Dim ref1, coord(2)
Dim longueur As AnyObject
Dim TheSpaWorkbench As SPAWorkbench

InputObject(0) = "Line"
Set Usel = CATIA.ActiveDocument.Selection
Set UselLB = Usel

Usel.Clear

oStatus = UselLB.SelectElement2(InputObject, "Selectionner le support", False)

If (oStatus = "Cancel") Then
Exit Sub
Else

TextBox1.Text = UselLB.Item2(1).Value.Name
MaDroite = UselLB.Item2(1).Value.Name

Set TheSpaWorkbench = CATIA.ActiveDocument.GetWorkbench("SPAWorkbench")
Set longueur = Usel.Item2(1).Value
Set Mesure = TheSpaWorkbench.GetMeasurable(longueur)
L = Mesure.Length / 2
End If

Bouton_ok.Enabled = True
Usel.Clear
Feuille_saisie.Show

End Sub

Private Sub UserForm_Initialize()
ComboBox1.AddItem "30*2"
ComboBox1.AddItem "30*1.5"
ComboBox1.AddItem "25*1.5"
ComboBox1.AddItem "20*1.5"
ComboBox1.AddItem "15*1.5"
End Sub

Attribute VB_Name = "Feuille_saisie_GDL"
Attribute VB_Base = "0{08C504BA-90E4-46EC-82AB-88DBC9D72929}{6FE09F49-B401-4A8C-807D-E65693B4AC1E}"
Attribute VB_GlobalNameSpace = False
Attribute VB_Creatable = False
Attribute VB_PredeclaredId = True
Attribute VB_Exposed = False
Attribute VB_TemplateDerived = False
Attribute VB_Customizable = False

Private Sub CommandButton1_Click()
Feuille_saisie_GDL.Hide

Dim Usel As Selection
Dim UselLB As Object
Dim InputObject(0)
Dim oStatus As String
Dim ref1, coord(2)


InputObject(0) = "Product"
Set Usel = CATIA.ActiveDocument.Selection
Set UselLB = Usel

Usel.Clear

oStatus = UselLB.SelectElement2(InputObject, "Selectionner le support", False)

If (oStatus = "Cancel") Then
Exit Sub
Else
ok_un = True
If ok_deux Then
    Bouton_ok.Enabled = True
End If
TextBox1.Text = UselLB.Item2(1).Value.PartNumber
SelRelimite = UselLB.Item2(1).Value.PartNumber

End If

Usel.Clear
Feuille_saisie_GDL.Show
End Sub

Private Sub CommandButton2_Click()
Feuille_saisie_GDL.Hide

Dim Usel As Selection
Dim UselLB As Object
Dim InputObject(0)
Dim oStatus As String
Dim ref1, coord(2)


InputObject(0) = "Product"
Set Usel = CATIA.ActiveDocument.Selection
Set UselLB = Usel


Usel.Clear

oStatus = UselLB.SelectElement2(InputObject, "Selectionner le support", False)

If (oStatus = "Cancel") Then
Exit Sub
Else

ok_deux = True
If ok_un Then
    Bouton_ok.Enabled = True
End If
TextBox2.Text = UselLB.Item2(1).Value.PartNumber
SelRelimitant = Usel.Item2(1).Value.PartNumber

End If

Usel.Clear
Feuille_saisie_GDL.Show
End Sub

Private Sub Bouton_ok_Click()
creation_GDL = "oui"
Feuille_saisie_GDL.Hide
End Sub
Private Sub Bouton_annuler_Click()
creation_GDL = "non"
fin_GDL = True
Feuille_saisie_GDL.Hide
End Sub

Attribute VB_Name = "GenerationTube"
' Definitions des variables globales
Public creation As String
Public fin As Boolean
Public R_ext As Single
Public R_int As Single
Public Dimension As String
Public MaDroite As String
Public Mesure As Measurable
Public L As Single

Sub CATMain()
'Le document
Dim ProdDocTube As ProductDocument
Dim ProdTube As Product
Dim ProdsTube As Products
Dim mon_tube As Product
Dim PartTube As PartDocument
Dim DocsTube As Documents
'La pièce
Dim tube As Part
Dim mes_corps_de_piece As Bodies
Dim corps_de_travail As Body
Dim mes_esquisses As Sketches
Dim ma_reference As Reference
Dim mon_esquisse As Sketch
Dim ma_construction2D As Factory2D
Dim cercle_ext As Circle2D
Dim cercle_int As Circle2D
Dim cercle_poche As Circle2D
Dim ma_forme As Pad
fin = False

Do 'Boucle d'affichage de la fenetre
Feuille_saisie.Show

If creation = "oui" Then
    ' Reconnaissance de la dimension de tube choisie dans la combobox
    If Dimension = "30*2" Then
        R_ext = 15
        R_int = 13
    End If
    If Dimension = "30*1.5" Then
        R_ext = 15
        R_int = 13.5
    End If
    If Dimension = "25*1.5" Then
        R_ext = 12.5
        R_int = 11
    End If
    If Dimension = "20*1.5" Then
        R_ext = 10
        R_int = 8.5
    End If
    If Dimension = "15*1.5" Then
        R_ext = 7.5
        R_int = 6
    End If
    'Création du doc type CatPart

    Set ProdDocTube = CATIA.ActiveDocument
    Set ProdTube = ProdDocTube.Product
    Set ProdsTube = ProdTube.Products
    Set mon_tube = ProdsTube.AddNewComponent("Part", "")
    Set DocsTube = CATIA.Documents
    Set PartTube = DocsTube.Item(mon_tube.PartNumber)
    
    'Création du tube dans le doc
    Set tube = PartTube.Part
    Set mes_corps_de_piece = tube.Bodies
    
    Set corps_de_travail = mes_corps_de_piece.Item("Corps principal")
    tube.InWorkObject = corps_de_travail
    Set mes_esquisses = corps_de_travail.Sketches
    
    'Creation d'une copie du support du tube
    
    Dim partDocument1 As PartDocument
    Set partDocument1 = DocsTube.Item("Filaire.CATPart")
    
    
    Dim selection1 As Selection
    Set selection1 = partDocument1.Selection
    
    selection1.Clear
    
    Dim part1 As Part
    Set part1 = partDocument1.Part
    
    Dim bodies1 As Bodies
    Set bodies1 = part1.Bodies
    
    Dim body1 As Body
    Set body1 = bodies1.Item("Corps principal")
    
    Dim hybridShapes2 As HybridShapes
    Set hybridShapes2 = body1.HybridShapes
    
    
    selection1.Add body1.HybridShapes.Item(MaDroite)
    selection1.Copy
    selection1.Clear
    
    
    Dim newselection As Selection
    Set newselection = CATIA.ActiveDocument.Selection
    newselection.Clear
    newselection.Add tube
    newselection.PasteSpecial "CATPrtResultWithOutLink"
    tube.Update
    
    'Création du plan normal à la droite
    Dim hybridShapeFactory1 As HybridShapeFactory
    Set hybridShapeFactory1 = tube.HybridShapeFactory
    
    Dim hybridShapes1 As HybridShapes
    Set hybridShapes1 = corps_de_travail.HybridShapes
    
    
    Dim reference1 As Reference
    Set reference1 = tube.CreateReferenceFromObject(hybridShapes1.Item("Droite.1"))
    
    Dim hybridShapePlaneNormal1 As HybridShapePlaneNormal
    Set hybridShapePlaneNormal1 = hybridShapeFactory1.AddNewPlaneNormal(reference1, Nothing)
    
    corps_de_travail.InsertHybridShape hybridShapePlaneNormal1
    
    tube.InWorkObject = hybridShapePlaneNormal1

    tube.Update

    'On se place dans l'esquisse
    
    Set ma_reference = tube.InWorkObject
    Set mon_esquisse = mes_esquisses.Add(ma_reference)
    
    tube.InWorkObject = mon_esquisse
    
    'Création des cercles intérieur et extérieur
    
    Set ma_construction2D = mon_esquisse.OpenEdition()
    Set cercle_ext = ma_construction2D.CreateClosedCircle(0, 0, R_ext)
    Set cercle_int = ma_construction2D.CreateClosedCircle(0, 0, R_int)
    mon_esquisse.CloseEdition
    
    'On se place dans le corps principal
    
    tube.InWorkObject = corps_de_travail
    Set ma_forme = tube.ShapeFactory.AddNewPad(mon_esquisse, L)
    ma_forme.IsSymmetric = True
    
    'Création esquisse pour gueule de loup
    
    Dim mysketch As Sketch
    Set mysketch = mes_esquisses.Add(hybridShapePlaneNormal1)
    
    Dim ma_construction2D2 As Factory2D
    Set ma_construction2D2 = mysketch.OpenEdition()
    
    Set cercle_poche = ma_construction2D2.CreateClosedCircle(0, 0, R_ext)
    
    mysketch.CloseEdition
    
    'Cacher le plan de construction
    
    Dim visPropertySet1 As VisPropertySet
    Dim selection2 As Selection
    Set selection2 = CATIA.ActiveDocument.Selection
    selection2.Add hybridShapePlaneNormal1
    Set visPropertySet1 = selection2.VisProperties
    visPropertySet1.SetShow 1
    
    'Cacher la droite de construction
    Dim visPropertySet2 As VisPropertySet
    Dim selection3 As Selection
    Set selection3 = CATIA.ActiveDocument.Selection
    selection3.Add hybridShapes1.Item("Droite.1")
    Set visPropertySet2 = selection3.VisProperties
    visPropertySet2.SetShow 1
    
    'Cacher l'esquisse pour gueule de loup
    Dim visPropertySet3 As VisPropertySet
    Dim selection4 As Selection
    Set selection4 = CATIA.ActiveDocument.Selection
    selection4.Add corps_de_travail.Sketches.Item("Esquisse.2")
    Set visPropertySet3 = selection4.VisProperties
    visPropertySet3.SetShow 1
    
    'Mise à jour du tube
    tube.Update
    CATIA.ActiveWindow.ActiveViewer.Reframe
Else
    MsgBox "Macro terminée"
End If
Loop While fin = False

End Sub

Attribute VB_Name = "Gueule_de_loup"
' Definition des variables globales
Public creation_GDL As String
Public SelRelimitant As String
Public SelRelimite As String
Public ok_un As Boolean
Public ok_deux As Boolean
Public fin_GDL As Boolean


Sub CATMain()

Dim GDLProdDoc As ProductDocument
Set GDLProdDoc = CATIA.ActiveDocument

Dim GDLDocs As Documents
Set GDLDocs = CATIA.Documents

ok_un = False
ok_deux = False
fin = False

Do
Feuille_saisie_GDL.Show

If creation_GDL = "oui" Then

'Recuperation esquisse tube relimitant
    
    Dim RelimitantPartDoc As PartDocument
    Set RelimitantPartDoc = GDLDocs.Item(SelRelimitant)
    
    Dim selection1 As Selection
    Set selection1 = CATIA.ActiveDocument.Selection
    
    Dim RelimitantPart As Part
    Set RelimitantPart = RelimitantPartDoc.Part
    
    Dim bodies1 As Bodies
    Set bodies1 = RelimitantPart.Bodies
    
    Dim body1 As Body
    Set body1 = bodies1.Item("Corps principal")
    
    
    Dim sketches1 As Sketches
    Set sketches1 = body1.Sketches
    
    Dim mysketch As Sketch
    Set mysketch = sketches1.Item("Esquisse.2")
    
    selection1.Clear
    selection1.Add mysketch
    selection1.Copy
    
    
    Dim RelimitePartDoc As PartDocument
    Set RelimitePartDoc = GDLDocs.Item(SelRelimite)
    
    Dim selection2 As Selection
    Set selection2 = CATIA.ActiveDocument.Selection
    
    Dim RelimitePart As Part
    Set RelimitePart = RelimitePartDoc.Part
    
    selection2.Clear
    selection2.Add RelimitePart
    selection2.PasteSpecial "CATPrtResult"
    
    RelimitePart.Update

'Changer le nom de l'esquisse
    
    Dim hybridBodies1 As HybridBodies
    Set hybridBodies1 = RelimitePart.HybridBodies
    
    Dim hybridBody1 As HybridBody
    Set hybridBody1 = hybridBodies1.Item("Références externes")
    
    Dim sketches2 As Sketches
    Set sketches2 = hybridBody1.HybridSketches
    
    Dim sketch2 As Sketch
    Set sketch2 = sketches2.Item(sketches2.Count)
    
    sketch2.Name = RelimitantPart.Name
    
'Creation de la poche

    Dim shapeFactory1 As ShapeFactory
    Set shapeFactory1 = RelimitePart.ShapeFactory
    
    Dim reference1 As Reference
    Set reference1 = RelimitePart.CreateReferenceFromName("")
    
    Dim pocket1 As Pocket
    Set pocket1 = shapeFactory1.AddNewPocketFromRef(reference1, 20#)
    
    Dim hybridBodies2 As HybridBodies
    Set hybridBodies2 = RelimitePart.HybridBodies
    
    Dim hybridBody2 As HybridBody
    Set hybridBody2 = hybridBodies2.Item("Références externes")
    
    Dim sketches3 As Sketches
    Set sketches3 = hybridBody2.HybridSketches
    
    Dim sketch3 As Sketch
    Set sketch3 = sketches3.Item(RelimitantPart.Name)
    
    Dim reference2 As Reference
    Set reference2 = RelimitePart.CreateReferenceFromObject(sketch3)
    
    pocket1.SetProfileElement reference2
    
    Dim limit1 As Limit
    Set limit1 = pocket1.FirstLimit
    
    Dim length1 As Length
    Set length1 = limit1.Dimension
    
    length1.Value = 200#
    
    pocket1.IsSymmetric = True
    
    RelimitantPart.UpdateObject pocket1

    

Else
    MsgBox "Macro terminée"

End If
Loop While fin_GDL = False

End Sub
