Attribute VB_Name = "Feuille_saisie"
Attribute VB_Base = "0{AF87055B-1328-42B4-9762-D4FC0D6A7C7A}{A239CC05-D4F8-4EC0-8632-A5A3170A2392}"
Attribute VB_GlobalNameSpace = False
Attribute VB_Creatable = False
Attribute VB_PredeclaredId = True
Attribute VB_Exposed = False
Attribute VB_TemplateDerived = False
Attribute VB_Customizable = False



Private Sub Bouton_OK_Click()
creation = "oui"
Dimension = ComboBox1.Value
Feuille_saisie.Hide
End Sub
Private Sub Bouton_annuler_Click()
creation = "non"
fin = True
Feuille_saisie.Hide
End Sub


Private Sub ComboBox1_Change()

End Sub

Private Sub CommandButton1_Click()
Feuille_saisie.Hide

Dim Usel As Selection
Dim UselLB As Object
Dim InputObject(0)
Dim oStatus As String
Dim Ref1, Coord(2)
Dim longueur As AnyObject
Dim TheSpaWorkbench As SPAWorkbench

InputObject(0) = "Line"
Set Usel = CATIA.ActiveDocument.Selection
Set UselLB = Usel

Usel.Clear

oStatus = UselLB.SelectElement2(InputObject, "Selectionner le support", False)

If (oStatus = "Cancel") Then
Exit Sub
Else

TextBox1.Text = UselLB.Item2(1).Value.Name
MaDroite = UselLB.Item2(1).Value.Name

Set TheSpaWorkbench = CATIA.ActiveDocument.GetWorkbench("SPAWorkbench")
Set longueur = Usel.Item2(1).Value
Set Mesure = TheSpaWorkbench.GetMeasurable(longueur)
L = Mesure.Length / 2
End If

Bouton_ok.Enabled = True
Usel.Clear
Feuille_saisie.Show

End Sub








Private Sub CommandButton2_Click()

Feuille_saisie.Hide

Dim Usel As Selection
Dim UselLB As Object
Dim InputObject(0)
Dim oStatus As String



InputObject(0) = "Product"
Set Usel = CATIA.ActiveDocument.Selection
Set UselLB = Usel

Usel.Clear

oStatus = UselLB.SelectElement2(InputObject, "Selectionner le support", False)

If (oStatus = "Cancel") Then
Exit Sub
Else
ok_un = True
If ok_deux Then
    Bouton_ok.Enabled = True
End If
SelFilaire = UselLB.Item2(1).Value.PartNumber
MsgBox SelFilaire
nom.Text = UselLB.Item2(1).Value.PartNumber


End If

Usel.Clear
Feuille_saisie.Show

End Sub

Private Sub Label1_Click()

End Sub

Private Sub nom_Change()

End Sub

Private Sub UserForm_Initialize()
ComboBox1.AddItem "30*2"
ComboBox1.AddItem "30*1.5"
ComboBox1.AddItem "25*1.5"
ComboBox1.AddItem "20*1.5"
ComboBox1.AddItem "15*1.5"
End Sub

Attribute VB_Name = "Feuille_saisie_GDL"
Attribute VB_Base = "0{CA3D03AF-BF2B-4148-9EB5-AA3C6597C5E8}{8A4692AA-1B86-4402-A3CE-62D0C6591E35}"
Attribute VB_GlobalNameSpace = False
Attribute VB_Creatable = False
Attribute VB_PredeclaredId = True
Attribute VB_Exposed = False
Attribute VB_TemplateDerived = False
Attribute VB_Customizable = False


Private Sub CommandButton1_Click()
Feuille_saisie_GDL.Hide

Dim Usel As Selection
Dim UselLB As Object
Dim InputObject(0)
Dim oStatus As String
Dim Ref1, Coord(2)


InputObject(0) = "Product"
Set Usel = CATIA.ActiveDocument.Selection
Set UselLB = Usel

Usel.Clear

oStatus = UselLB.SelectElement2(InputObject, "Selectionner le support", False)

If (oStatus = "Cancel") Then
Exit Sub
Else
ok_un = True
If ok_deux Then
    Bouton_ok.Enabled = True
End If
TextBox1.Text = UselLB.Item2(1).Value.PartNumber
SelRelimite = UselLB.Item2(1).Value.PartNumber

End If

Usel.Clear
Feuille_saisie_GDL.Show
End Sub

Private Sub CommandButton2_Click()
Feuille_saisie_GDL.Hide

Dim Usel As Selection
Dim UselLB As Object
Dim InputObject(0)
Dim oStatus As String
Dim Ref1, Coord(2)


InputObject(0) = "Product"
Set Usel = CATIA.ActiveDocument.Selection
Set UselLB = Usel


Usel.Clear

oStatus = UselLB.SelectElement2(InputObject, "Selectionner le support", False)

If (oStatus = "Cancel") Then
Exit Sub
Else

ok_deux = True
If ok_un Then
    Bouton_ok.Enabled = True
End If
TextBox2.Text = UselLB.Item2(1).Value.PartNumber
SelRelimitant = Usel.Item2(1).Value.PartNumber

End If

Usel.Clear
Feuille_saisie_GDL.Show
End Sub

Private Sub Bouton_OK_Click()
creation_GDL = "oui"
Feuille_saisie_GDL.Hide
End Sub
Private Sub Bouton_annuler_Click()
creation_GDL = "non"
fin_GDL = True
Feuille_saisie_GDL.Hide
End Sub

Attribute VB_Name = "Feuille_saisie_GDLBiseau"
Attribute VB_Base = "0{50461F30-D5DF-4D74-98BF-996BC61E1CD6}{15E58387-48DA-46C0-81E8-10CCA86D169F}"
Attribute VB_GlobalNameSpace = False
Attribute VB_Creatable = False
Attribute VB_PredeclaredId = True
Attribute VB_Exposed = False
Attribute VB_TemplateDerived = False
Attribute VB_Customizable = False
Private Sub Bouton_annuler_Click()

creationGDL = "non"
fin = True
Feuille_saisie_GDLBiseau.Hide

End Sub





Private Sub Bouton_OK_Click()
creationGDL = "oui"
Feuille_saisie_GDLBiseau.Hide
Nbx_GDL_Biseau = Feuille_saisie_GDLBiseau.Nbx.Value
End Sub




Private Sub ChoixFace_Click()
Feuille_saisie_GDLBiseau.Hide

Dim Usel As Selection
Dim UselLB As Object
Dim InputObject(0)
Dim oStatus As String



InputObject(0) = "Face"
Set Usel = CATIA.ActiveDocument.Selection
Set UselLB = Usel

Usel.Clear

oStatus = UselLB.SelectElement2(InputObject, "Selectionner le support", False)

If (oStatus = "Cancel") Then
Exit Sub
Else
ok_un = True
If ok_deux Then
    Bouton_ok.Enabled = True
End If
Face = UselLB.Item2(1).Value.Name
MsgBox Face
nom6.Text = UselLB.Item2(1).Value.Name


End If

Usel.Clear
Feuille_saisie_GDLBiseau.Show
End Sub

Private Sub ChoixPts1_Click()
Feuille_saisie_GDLBiseau.Hide

Dim Usel As Selection
Dim UselLB As Object
Dim InputObject(0)
Dim oStatus As String
Dim X As Double, Y As Double, Z As Double
Dim elt1, Coord(2), Ref1

InputObject(0) = "Vertex"
Set Usel = CATIA.ActiveDocument.Selection
Set UselLB = Usel

Usel.Clear

oStatus = UselLB.SelectElement2(InputObject, "Selectionner le support", False)

If (oStatus = "Cancel") Then
Exit Sub
Else


Set elt1 = Usel.Item2(1)
    elt1.GetCoordinates Coord
        X1 = Coord(0)
        Y1 = Coord(1)
        Z1 = Coord(2)


nom.Text = "Point sélectionné"


End If

Usel.Clear
Feuille_saisie_GDLBiseau.Show
End Sub


Private Sub ChoixPts2_Click()
Feuille_saisie_GDLBiseau.Hide

Dim Usel As Selection
Dim UselLB As Object
Dim InputObject(0)
Dim oStatus As String
Dim X As Double, Y As Double, Z As Double
Dim elt1, Coord(2), Ref1

InputObject(0) = "Vertex"
Set Usel = CATIA.ActiveDocument.Selection
Set UselLB = Usel

Usel.Clear

oStatus = UselLB.SelectElement2(InputObject, "Selectionner le support", False)

If (oStatus = "Cancel") Then
Exit Sub
Else


Set elt1 = Usel.Item2(1)
    elt1.GetCoordinates Coord
        X2 = Coord(0)
        Y2 = Coord(1)
        Z2 = Coord(2)


nom2.Text = "Point sélectionné"

End If

Usel.Clear
Feuille_saisie_GDLBiseau.Show
End Sub


Private Sub ChoixPts3_Click()
Feuille_saisie_GDLBiseau.Hide

Dim Usel As Selection
Dim UselLB As Object
Dim InputObject(0)
Dim oStatus As String
Dim X As Double, Y As Double, Z As Double
Dim elt1, Coord(2), Ref1

InputObject(0) = "Vertex"
Set Usel = CATIA.ActiveDocument.Selection
Set UselLB = Usel

Usel.Clear

oStatus = UselLB.SelectElement2(InputObject, "Selectionner le support", False)

If (oStatus = "Cancel") Then
Exit Sub
Else


Set elt1 = Usel.Item2(1)
    elt1.GetCoordinates Coord
        X3 = Coord(0)
        Y3 = Coord(1)
        Z3 = Coord(2)


nom3.Text = "Point sélectionné"


End If

Usel.Clear
Feuille_saisie_GDLBiseau.Show
End Sub






Private Sub ChoixPart_Click()
Feuille_saisie_GDLBiseau.Hide

Dim Usel As Selection
Dim UselLB As Object
Dim InputObject(0)
Dim oStatus As String



InputObject(0) = "Part"
Set Usel = CATIA.ActiveDocument.Selection
Set UselLB = Usel

Usel.Clear

oStatus = UselLB.SelectElement2(InputObject, "Selectionner le support", False)

If (oStatus = "Cancel") Then
Exit Sub
Else
ok_un = True
If ok_deux Then
    Bouton_ok.Enabled = True
End If
SelTubePart = UselLB.Item2(1).Value.Name
MsgBox SelTubePart
nom5.Text = UselLB.Item2(1).Value.Name


End If

Usel.Clear
Feuille_saisie_GDLBiseau.Show
End Sub







Private Sub UserForm_Click()

End Sub

Attribute VB_Name = "Generation_GDL"
' Definition des variables globales
Public creation_GDL As String
Public SelRelimitant As String
Public SelRelimite As String
Public ok_un As Boolean
Public ok_deux As Boolean
Public fin_GDL As Boolean


Sub CATMain()

Dim GDLProdDoc As ProductDocument
Set GDLProdDoc = CATIA.ActiveDocument

Dim GDLDocs As Documents
Set GDLDocs = CATIA.Documents

ok_un = False
ok_deux = False
fin = False

Do
Feuille_saisie_GDL.Show

If creation_GDL = "oui" Then

'Recuperation esquisse tube relimitant
    
    Dim RelimitantPartDoc As PartDocument
    Set RelimitantPartDoc = GDLDocs.Item(SelRelimitant + ".CATPart")
    
    Dim selection1 As Selection
    Set selection1 = CATIA.ActiveDocument.Selection
    
    Dim RelimitantPart As Part
    Set RelimitantPart = RelimitantPartDoc.Part
    
    Dim bodies1 As Bodies
    Set bodies1 = RelimitantPart.Bodies
    
    Dim body1 As Body
    Set body1 = bodies1.Item("Corps principal")
    
    
    Dim sketches1 As Sketches
    Set sketches1 = body1.Sketches
    
    Dim mysketch As Sketch
    Set mysketch = sketches1.Item("Esquisse.2")
    
    selection1.Clear
    selection1.Add mysketch
    selection1.Copy
    
    
    Dim RelimitePartDoc As PartDocument
    Set RelimitePartDoc = GDLDocs.Item(SelRelimite + ".CATPart")
    
    Dim selection2 As Selection
    Set selection2 = CATIA.ActiveDocument.Selection
    
    Dim RelimitePart As Part
    Set RelimitePart = RelimitePartDoc.Part
    
    selection2.Clear
    selection2.Add RelimitePart
    selection2.PasteSpecial "CATPrtResult"
    
    RelimitePart.Update

'Changer le nom de l'esquisse
    
    Dim hybridBodies1 As HybridBodies
    Set hybridBodies1 = RelimitePart.HybridBodies
    
    Dim hybridBody1 As HybridBody
    Set hybridBody1 = hybridBodies1.Item("Références externes")
    
    Dim sketches2 As Sketches
    Set sketches2 = hybridBody1.HybridSketches
    
    Dim sketch2 As Sketch
    Set sketch2 = sketches2.Item(sketches2.Count)
    
    sketch2.Name = RelimitantPart.Name
    
'Creation de la poche

    Dim shapeFactory1 As ShapeFactory
    Set shapeFactory1 = RelimitePart.ShapeFactory
    
    Dim reference1 As Reference
    Set reference1 = RelimitePart.CreateReferenceFromName("")
    
    Dim pocket1 As Pocket
    Set pocket1 = shapeFactory1.AddNewPocketFromRef(reference1, 20#)
    
    Dim hybridBodies2 As HybridBodies
    Set hybridBodies2 = RelimitePart.HybridBodies
    
    Dim hybridBody2 As HybridBody
    Set hybridBody2 = hybridBodies2.Item("Références externes")
    
    Dim sketches3 As Sketches
    Set sketches3 = hybridBody2.HybridSketches
    
    Dim sketch3 As Sketch
    Set sketch3 = sketches3.Item(RelimitantPart.Name)
    
    Dim reference2 As Reference
    Set reference2 = RelimitePart.CreateReferenceFromObject(sketch3)
    
    pocket1.SetProfileElement reference2
    
    Dim limit1 As Limit
    Set limit1 = pocket1.FirstLimit
    
    Dim length1 As Length
    Set length1 = limit1.Dimension
    
    length1.Value = 200#
    
    pocket1.IsSymmetric = True
    
    RelimitantPart.UpdateObject pocket1

    

Else
    MsgBox "Macro terminée"

End If
Loop While fin_GDL = False

End Sub

Attribute VB_Name = "Generation_GDL_Biseau"
'___________________Definition des variables___________________
'Variable pour le fonctionnement
Public creationGDL As String
Public Nbx_GDL_Biseau As Integer


'Coordonnees du premier point entre par user
Public X1 As Double
Public Y1 As Double
Public Z1 As Double

'Coordonnees du deuxieme point entre par user
Public X2 As Double
Public Y2 As Double
Public Z2 As Double

'Coordonnees du troisieme point entre par user
Public X3 As Double
Public Y3 As Double
Public Z3 As Double

'Definition des deux normes utilisees
Public N1 As Double
Public N2 As Double



'Choix de la piece a modifier (product et part)
Public Face As String
Public SelTubePart As String
'_______________Fin de la declaration des variables_________________________






'________________Debut du code principal ___________________________________

Sub CATMain()
Do
Feuille_saisie_GDLBiseau.Show
If creationGDL = "oui" Then


'______________Calul des coefficient de l'equation du plan a respecter
Dim N1, N2 As Double
Dim X4, Y4, Z4 As Double
Dim X5, Y5, Z5 As Double
Dim A, B, C, D As Double

'Calcul des normes
 N1 = (((X2 - X1) ^ 2 + (Y2 - Y1) ^ 2 + (Z2 - Z1) ^ 2)) ^ 0.5
 N2 = (((X3 - X2) ^ 2 + (Y3 - Y2) ^ 2 + (Z3 - Z2) ^ 2)) ^ 0.5

'Calcul des coordonnées des points intermediaires
 X4 = X2 - (20 / N1) * (X2 - X1)
 Y4 = Y2 - (20 / N1) * (Y2 - Y1)
 Z4 = Z2 - (20 / N1) * (Z2 - Z1)


 X5 = X2 + (20 / N2) * (X3 - X2)
 Y5 = Y2 + (20 / N2) * (Y3 - Y2)
 Z5 = Z2 + (20 / N2) * (Z3 - Z2)


 A = X4 - X5
 B = Y4 - Y5
 C = Z4 - Z5
 D = (A * X2) + (B * Y2) + (C * Z2)




'_____________Code de creation du plan dans la piece à modifier
Dim documents1 As Documents
Set documents1 = CATIA.Documents

Dim partDocument1 As PartDocument
Set partDocument1 = documents1.Item(SelTubePart + ".CATPart")

Dim part1 As Part
Set part1 = partDocument1.Part

Dim hybridShapeFactory1 As HybridShapeFactory
Set hybridShapeFactory1 = part1.HybridShapeFactory

Dim hybridShapePlaneEquation1 As HybridShapePlaneEquation
Set hybridShapePlaneEquation1 = hybridShapeFactory1.AddNewPlaneEquation(A, B, C, D) 'On entre les coefficients de l'équation du plan

Dim axisSystems1 As AxisSystems
Set axisSystems1 = part1.AxisSystems

Dim axisSystem1 As AxisSystem
Set axisSystem1 = axisSystems1.Item("Repère absolu")

Dim reference1 As Reference
Set reference1 = part1.CreateReferenceFromObject(axisSystem1)

hybridShapePlaneEquation1.RefAxisSystem = reference1

Dim bodies1 As Bodies
Set bodies1 = part1.Bodies

Dim body1 As Body
Set body1 = bodies1.Item("Corps principal")

body1.InsertHybridShape hybridShapePlaneEquation1

part1.InWorkObject = hybridShapePlaneEquation1

part1.Update


'_______________Creation de l'extrusion jusqu'au plan


Dim documents41 As Documents
Set documents41 = CATIA.Documents

Dim partDocument41 As PartDocument
Set partDocument41 = documents41.Item(SelTubePart + ".CATPart")

Dim part41 As Part
Set part41 = partDocument41.Part

Dim bodies41 As Bodies
Set bodies41 = part41.Bodies

Dim body41 As Body
Set body41 = bodies41.Item("Corps principal")

Dim sketches41 As Sketches
Set sketches41 = body41.Sketches

Dim reference41 As Reference
Set reference41 = part41.CreateReferenceFromName(Face)

Dim sketch41 As Sketch
Set sketch41 = sketches41.Add(reference41)

Dim arrayOfVariantOfDouble1(8)
arrayOfVariantOfDouble1(0) = X2 'On centre l'esquisse sur le point numéro 2
arrayOfVariantOfDouble1(1) = Y2
arrayOfVariantOfDouble1(2) = Z2
arrayOfVariantOfDouble1(3) = -1#
arrayOfVariantOfDouble1(4) = 0#
arrayOfVariantOfDouble1(5) = 0#
arrayOfVariantOfDouble1(6) = 0#
arrayOfVariantOfDouble1(7) = 0.707107
arrayOfVariantOfDouble1(8) = 0.707107
Set sketch1Variant = sketch41
sketch1Variant.SetAbsoluteAxisData arrayOfVariantOfDouble1

part41.InWorkObject = sketch41

Dim factory2D1 As Factory2D
Set factory2D1 = sketch41.OpenEdition()

Dim geometricElements1 As GeometricElements
Set geometricElements1 = sketch41.GeometricElements

Dim axis2D1 As Axis2D
Set axis2D1 = geometricElements1.Item("Repère")

Dim line2D1 As Line2D
Set line2D1 = axis2D1.GetItem("Axe horizontal")

line2D1.ReportName = 1

Dim line2D2 As Line2D
Set line2D2 = axis2D1.GetItem("Axe vertical")

line2D2.ReportName = 2

Dim circle2D1 As Circle2D
Set circle2D1 = factory2D1.CreateClosedCircle(0#, 0#, 15#)

Dim point2D1 As Point2D
Set point2D1 = axis2D1.GetItem("Origine")

circle2D1.CenterPoint = point2D1

circle2D1.ReportName = 3

Dim shapes41 As Shapes
Set shapes41 = body41.Shapes

Dim pad41 As Pad
Set pad41 = shapes41.Item("Extrusion.1")

Dim reference42 As Reference
Set reference42 = part41.CreateReferenceFromBRepName("FEdge:(Edge:(Face:(Brp:(Pad.1;0:(Brp:(Sketch.1;1)));None:();Cf12:());Face:(Brp:(Pad.1;2);None:();Cf12:());None:(Limits1:();Limits2:());Cf12:());WithPermanentBody;WithoutBuildError;WithInitialFeatureSupport;MonoFond;MFBRepVersion_CXR29)", pad41)

Dim geometricElements42 As GeometricElements
Set geometricElements42 = factory2D1.CreateProjections(reference42)

Dim geometry2D1 As Geometry2D
Set geometry2D1 = geometricElements42.Item("Empreinte.1")

geometry2D1.Construction = True

Dim circle2D2 As Circle2D
Set circle2D2 = factory2D1.CreateClosedCircle(0#, 0#, 7#)

circle2D2.CenterPoint = point2D1

circle2D2.ReportName = 4

Dim reference43 As Reference
Set reference43 = part41.CreateReferenceFromBRepName("FEdge:(Edge:(Face:(Brp:(Pad.1;2);None:();Cf12:());Face:(Brp:(Pad.1;0:(Brp:(Sketch.1;2)));None:();Cf12:());None:(Limits1:();Limits2:());Cf12:());WithPermanentBody;WithoutBuildError;WithInitialFeatureSupport;MonoFond;MFBRepVersion_CXR29)", pad41)

Dim geometricElements3 As GeometricElements
Set geometricElements3 = factory2D1.CreateProjections(reference43)

Dim geometry2D2 As Geometry2D
Set geometry2D2 = geometricElements3.Item("Empreinte.1")

geometry2D2.Construction = True

Dim constraints1 As Constraints
Set constraints1 = sketch41.Constraints

Dim reference44 As Reference
Set reference44 = part41.CreateReferenceFromObject(circle2D1)

Dim reference45 As Reference
Set reference45 = part41.CreateReferenceFromObject(geometry2D1)

Dim constraint1 As Constraint
Set constraint1 = constraints1.AddBiEltCst(catCstTypeDistance, reference44, reference45)

constraint1.Mode = catCstModeDrivingDimension

Dim length1 As Length
Set length1 = constraint1.Dimension

length1.Value = 0#

Dim reference46 As Reference
Set reference46 = part41.CreateReferenceFromObject(circle2D2)

Dim reference47 As Reference
Set reference47 = part41.CreateReferenceFromObject(geometry2D2)

Dim constraint2 As Constraint
Set constraint2 = constraints1.AddBiEltCst(catCstTypeDistance, reference46, reference47)

constraint2.Mode = catCstModeDrivingDimension

Dim length2 As Length
Set length2 = constraint2.Dimension

length2.Value = 0#

sketch41.CloseEdition

part41.InWorkObject = sketch41

part41.Update

Dim shapeFactory41 As ShapeFactory
Set shapeFactory41 = part41.ShapeFactory

Dim pad42 As Pad
Set pad42 = shapeFactory41.AddNewPad(sketch41, 20#)

Dim limit41 As Limit
Set limit41 = pad42.FirstLimit

limit41.LimitMode = catUpToPlaneLimit

Dim hybridShapes41 As HybridShapes
Set hybridShapes41 = body41.HybridShapes

Dim hybridShapePlaneEquation41 As HybridShapePlaneEquation

If Nbx_GDL_Biseau = 0 Then
Set hybridShapePlaneEquation41 = hybridShapes41.Item("Plan.2")
Else
Set hybridShapePlaneEquation41 = hybridShapes41.Item("Plan.3")
End If

Dim reference48 As Reference
Set reference48 = part41.CreateReferenceFromObject(hybridShapePlaneEquation41)

limit41.LimitingElement = reference48

part41.Update

Dim pocket41 As Pocket
Set pocket41 = shapeFactory41.AddNewPocket(sketch41, 20#)

Dim limit42 As Limit
Set limit42 = pocket41.FirstLimit

limit42.LimitMode = catUpToPlaneLimit

Dim reference49 As Reference
Set reference49 = part41.CreateReferenceFromObject(hybridShapePlaneEquation41)

limit42.LimitingElement = reference49

part41.Update









Feuille_saisie_GDLBiseau.Show

Else
MsgBox "Macro terminée"

End If
Loop While fin = False

End Sub

Attribute VB_Name = "Generation_tubes"
' Definitions des variables globales
Public creation As String
Public fin As Boolean
Public R_ext As Single
Public R_int As Single
Public Dimension As String
Public MaDroite As String
Public Mesure As Measurable
Public L As Single
Public SelFilaire As String


Sub CATMain()
'Le document
Dim ProdDocTube As ProductDocument
Dim ProdTube As Product
Dim ProdsTube As Products
Dim mon_tube As Product
Dim PartTube As PartDocument
Dim DocsTube As Documents


'La pièce
Dim tube As Part
Dim mes_corps_de_piece As Bodies
Dim corps_de_travail As Body
Dim mes_esquisses As Sketches
Dim ma_reference As Reference
Dim mon_esquisse As Sketch
Dim ma_construction2D As Factory2D
Dim cercle_ext As Circle2D
Dim cercle_int As Circle2D
Dim cercle_poche As Circle2D
Dim ma_forme As Pad
fin = False

Do 'Boucle d'affichage de la fenetre
Feuille_saisie.Show

If creation = "oui" Then
    ' Reconnaissance de la dimension de tube choisie dans la combobox
    ' On associe le choix de l'utilisateur aux variables concernées
    If Dimension = "30*2" Then
        R_ext = 15
        R_int = 13
    End If
    If Dimension = "30*1.5" Then
        R_ext = 15
        R_int = 13.5
    End If
    If Dimension = "25*1.5" Then
        R_ext = 12.5
        R_int = 11
    End If
    If Dimension = "20*1.5" Then
        R_ext = 10
        R_int = 8.5
    End If
    If Dimension = "15*1.5" Then
        R_ext = 7.5
        R_int = 6
    End If
    
    
    
    
    
    
    'Création du doc type CatPart

    Set ProdDocTube = CATIA.ActiveDocument
    Set ProdTube = ProdDocTube.Product
    Set ProdsTube = ProdTube.Products
    Set mon_tube = ProdsTube.AddNewComponent("Part", "")
    Set DocsTube = CATIA.Documents
    Set PartTube = DocsTube.Item(mon_tube.PartNumber + ".CATPart")
    
    
    
    
    
    'Création du tube dans le doc
    Set tube = PartTube.Part
    Set mes_corps_de_piece = tube.Bodies
    
    Set corps_de_travail = mes_corps_de_piece.Item("Corps principal")
    tube.InWorkObject = corps_de_travail
    Set mes_esquisses = corps_de_travail.Sketches
    
    
    
    
    
    
    
    'Creation d'une copie du support du tube
    
    
    Dim partDocument1 As PartDocument
    Set partDocument1 = DocsTube.Item(SelFilaire + ".CATPart")
    
    
    Dim selection1 As Selection
    Set selection1 = partDocument1.Selection
    
    selection1.Clear
    
    Dim part1 As Part
    Set part1 = partDocument1.Part
    
    Dim bodies1 As Bodies
    Set bodies1 = part1.Bodies
    
    Dim body1 As Body
    Set body1 = bodies1.Item("Corps principal")
    
    Dim hybridShapes2 As HybridShapes
    Set hybridShapes2 = body1.HybridShapes
    
    
    selection1.Add body1.HybridShapes.Item(MaDroite)
    selection1.Copy
    selection1.Clear
    
    
    Dim newselection As Selection
    Set newselection = CATIA.ActiveDocument.Selection
    newselection.Clear
    newselection.Add tube
    newselection.PasteSpecial "CATPrtResultWithOutLink"
    tube.Update
    
    
    
    
    
    
    
    
    'Création du plan normal à la droite
    Dim hybridShapeFactory1 As HybridShapeFactory
    Set hybridShapeFactory1 = tube.HybridShapeFactory
    
    Dim hybridShapes1 As HybridShapes
    Set hybridShapes1 = corps_de_travail.HybridShapes
    
    
    Dim reference1 As Reference
    Set reference1 = tube.CreateReferenceFromObject(hybridShapes1.Item("Droite.1"))
    
    Dim hybridShapePlaneNormal1 As HybridShapePlaneNormal
    Set hybridShapePlaneNormal1 = hybridShapeFactory1.AddNewPlaneNormal(reference1, Nothing)
    
    corps_de_travail.InsertHybridShape hybridShapePlaneNormal1
    
    tube.InWorkObject = hybridShapePlaneNormal1

    tube.Update







    'On se place dans l'esquisse
    
    Set ma_reference = tube.InWorkObject
    Set mon_esquisse = mes_esquisses.Add(ma_reference)
    
    tube.InWorkObject = mon_esquisse
    
    
    
    
    
    
    
    'Création des cercles intérieur et extérieur
    
    Set ma_construction2D = mon_esquisse.OpenEdition()
    Set cercle_ext = ma_construction2D.CreateClosedCircle(0, 0, R_ext)
    Set cercle_int = ma_construction2D.CreateClosedCircle(0, 0, R_int)
    mon_esquisse.CloseEdition
    
    
    
    'On se place dans le corps principal
    
    tube.InWorkObject = corps_de_travail
    Set ma_forme = tube.ShapeFactory.AddNewPad(mon_esquisse, L)
    ma_forme.IsSymmetric = True
    
    
    
    
    
    
    
    'Création esquisse pour gueule de loup
    
    Dim mysketch As Sketch
    Set mysketch = mes_esquisses.Add(hybridShapePlaneNormal1)
    
    Dim ma_construction2D2 As Factory2D
    Set ma_construction2D2 = mysketch.OpenEdition()
    
    Set cercle_poche = ma_construction2D2.CreateClosedCircle(0, 0, R_ext)
    
    mysketch.CloseEdition
    
    
    
    
    
    
    
    'Cacher le plan de construction
    
    Dim visPropertySet1 As VisPropertySet
    Dim selection2 As Selection
    Set selection2 = CATIA.ActiveDocument.Selection
    selection2.Add hybridShapePlaneNormal1
    Set visPropertySet1 = selection2.VisProperties
    visPropertySet1.SetShow 1
    
    
    
    
    
    
    
    'Cacher la droite de construction
    Dim visPropertySet2 As VisPropertySet
    Dim selection3 As Selection
    Set selection3 = CATIA.ActiveDocument.Selection
    selection3.Add hybridShapes1.Item("Droite.1")
    Set visPropertySet2 = selection3.VisProperties
    visPropertySet2.SetShow 1
    
    
    
    
    
    
    'Cacher l'esquisse pour gueule de loup
    Dim visPropertySet3 As VisPropertySet
    Dim selection4 As Selection
    Set selection4 = CATIA.ActiveDocument.Selection
    selection4.Add corps_de_travail.Sketches.Item("Esquisse.2")
    Set visPropertySet3 = selection4.VisProperties
    visPropertySet3.SetShow 1
    
    
    
    
    
    
    
    
    
    'Mise à jour du tube
    tube.Update
    CATIA.ActiveWindow.ActiveViewer.Reframe
Else
    MsgBox "Macro terminée"
End If
Loop While fin = False

End Sub
