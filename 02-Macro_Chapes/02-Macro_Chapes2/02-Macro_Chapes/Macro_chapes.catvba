Attribute VB_Name = "Fenetre_Selection"
Attribute VB_Base = "0{052740B9-8152-4FC9-8396-5A34045A1DA8}{2363954E-8F83-4F16-AEDA-A0E44D93CFCE}"
Attribute VB_GlobalNameSpace = False
Attribute VB_Creatable = False
Attribute VB_PredeclaredId = True
Attribute VB_Exposed = False
Attribute VB_TemplateDerived = False
Attribute VB_Customizable = False
Private Sub Button_pt_debut_Click()

    ' --------------------------
    ' Selection de publication pour l'axe
    ' --------------------------

    'Masque la fenêtre pour faire la sélection
    Fenetre_Selection.Hide
    
    'Déclaration des variables
    Dim USel As Selection
    Dim USelLB
    Dim InputObject(0)
    Dim oStatus
    InputObject(0) = "Publication"
    Set USel = CATIA.ActiveDocument.Selection
    Set USelLB = USel
    USel.Clear
    
    'Sélectionner un élément
    oStatus = USelLB.SelectElement2(InputObject, "Selectionnez une publication", False)
    If (oStatus = "Cancel") Then
        Exit Sub
    Else
        Set pt_debut_ref = USelLB.Item(1).Value.Parent.Item(USelLB.Item(1).Value.Name).Valuation
        Label_pt_debut.Caption = USelLB.Item(1).Value.Parent.Parent.Name & "_" & USelLB.Item(1).Value.Name
    End If
    
    'Tous les champs doivent être remplis
    is_pt_debut_selected = True
    'If is_pt_debut_selected * isFaceTeteSelected * isFaceEcrouSelected Then
        'obtenirLesMesures
    'End If
    
    Creation_pt_debut
    'Affichage de la fenetre
    USel.Clear
    Fenetre_Selection.Show
End Sub



Public Sub Creation_pt_debut()

Dim RootDoc As Document
Dim RootProduct As Product
Dim AllProds As Products
Dim Mon_Prod As Product
Dim AllDocs As Documents
Dim Docpart1 As PartDocument

Set RootDoc = CATIA.ActiveDocument
Set RootProduct = RootDoc.Product
Set AllProds = RootProduct.Products
Set Mon_Prod = AllProds.AddNewComponent("Part", "")
Set AllDocs = CATIA.Documents
Set Docpart1 = AllDocs.Item(Mon_Prod.PartNumber + ".CATPart")


'Set Docpart1 = CATIA.Documents.Add("CATPart")   ' create new part   (use this code on an empty session of CATIA)

'Dim ActDoc As Document
'Set ActDoc = CATIA.ActiveDocument             ' Makes the Current Document the Active one

Dim HSF As HybridShapeFactory
Dim MaPart As Part
Set MaPart = Docpart1.Part
Set HSF = MaPart.HybridShapeFactory       ' Provides the Shape Factory

'  Retrieving HybridBodies collection in Part Document

Dim Listbodies As Bodies
Set Listbodies = MaPart.Bodies


Dim B1 As Body
Set B1 = Listbodies.Item("Corps principal")

MaPart.InWorkObject = B1

Dim my_shapes As HybridShapes
Set my_shapes = B1.HybridShapes

Dim ma_ref As Reference
Set ma_ref = pt_debut_ref

Dim my_point As point
'Set my_point = my_shapes.
'Dim point As Reference
'Set point = part1.Part.CreateReferenceFromBRepName(pt_debut_ref, pt_debut_ref.Parent)


Dim First_Point As HybridShapePointCoord

Set First_Point = HSF.AddNewPointCoordWithReference(0, 0, 0, ma_ref)
'Set pt_debut = B1.AddNewPointCoord(0, 10, 0)

Fenetre_Selection.Show



End Sub

Attribute VB_Name = "Generation_chapes"
Sub CATMain()

End Sub

Attribute VB_Name = "Module_variables"
' --------------------------------------
' Création des variables globales
' --------------------------------------

' Variables de l'emplacement des élements de référence
Public pt_debut_ref As Reference

Public is_pt_debut_selected As Boolean

Attribute VB_Name = "test"
Sub CATMain()

Dim documents1 As Documents
Set documents1 = CATIA.Documents

Dim partDocument1 As PartDocument
Set partDocument1 = documents1.Item("Part3.CATPart")

Dim part1 As Part
Set part1 = partDocument1.Part

Dim hybridShapeFactory1 As HybridShapeFactory
Set hybridShapeFactory1 = part1.HybridShapeFactory

Dim hybridShapePointCoord1 As HybridShapePointCoord
Set hybridShapePointCoord1 = hybridShapeFactory1.AddNewPointCoord(0#, 0#, 0#)

Dim axisSystems1 As AxisSystems
Set axisSystems1 = part1.AxisSystems

Dim axisSystem1 As AxisSystem
Set axisSystem1 = axisSystems1.Item("Repère absolu")

Dim reference1 As Reference
Set reference1 = part1.CreateReferenceFromObject(axisSystem1)

hybridShapePointCoord1.RefAxisSystem = reference1

Dim bodies1 As Bodies
Set bodies1 = part1.Bodies

Dim body1 As Body
Set body1 = bodies1.Item("Corps principal")

body1.InsertHybridShape hybridShapePointCoord1

part1.InWorkObject = hybridShapePointCoord1

part1.Update

End Sub
