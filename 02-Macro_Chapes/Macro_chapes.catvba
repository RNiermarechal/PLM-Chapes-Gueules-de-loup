Attribute VB_Name = "Fenetre_Selection"
Attribute VB_Base = "0{58204176-878B-44BB-9EAA-557E0FB95D15}{A1975943-7879-4DB2-9488-65B2554F591F}"
Attribute VB_GlobalNameSpace = False
Attribute VB_Creatable = False
Attribute VB_PredeclaredId = True
Attribute VB_Exposed = False
Attribute VB_TemplateDerived = False
Attribute VB_Customizable = False
Private Sub Button_init_part_Click()

'Creation de l'arborescence active
Set RootDoc = CATIA.ActiveDocument
Set RootProduct = RootDoc.Product
Set AllProds = RootProduct.Products

'Création d'une part dans l'arborescence active
Set Mon_Prod = AllProds.AddNewComponent("Part", "") 'faire dans la meme part pour la suite
Set AllDocs = CATIA.Documents
Set Docpart1 = AllDocs.Item(Mon_Prod.PartNumber + ".CATPart") 'Remplacer Mon_Prod.PartNumber + ".CATPart" par Ma_piece.CATPart
Set my_part = Docpart1.Part


Set HSF = my_part.HybridShapeFactory

'Récupère HybridBodies collection dans Part Document
Set Listbodies = my_part.Bodies

'Crée le corps de travail et le défini comme corps de travail de la part créée
Set B1 = Listbodies.Item("Corps principal")
my_part.InWorkObject = B1

Set my_shapes = B1.HybridShapes

End Sub

Private Sub Button_pt_debut_Click()

' --------------------------
' Selection de points pour former axe
' --------------------------

'Masque la fenêtre pour faire la sélection
Fenetre_Selection.Hide
    
'Déclaration des variables
'Dim USel As Selection
Dim USelection As Object
Dim InputObject(0)
Dim oStatus
Dim elt1, Coord(2), ref1
Dim x As Double, y As Double, z As Double
    
Dim TheSPAWorkbench As SPAWorkbench
Set TheSPAWorkbench = RootDoc.GetWorkbench("SPAWorkbench")
    
Dim TheMeasurable As Measurable
Dim vTheMeasurable
    
'Dim acoord_in_part(2)
     
InputObject(0) = "Vertex" 'c'est un filtre (le curseur ne selectionne que ça). Vertex = sommets d'une géo 3D

Set USelection = CATIA.ActiveDocument.Selection
'Set USelLB = USel
USelection.Clear
    
'Sélectionner un élément
oStatus = USelection.SelectElement2(InputObject, "Selectionnez une publication", False)
If (oStatus = "Cancel") Then
    Exit Sub
Else
    Set elt1 = USelection.Item2(1)
    If elt1.Type = "Vertex" Then
        elt1.GetCoordinates Coord
        x = Coord(0)
        y = Coord(1)
        z = Coord(2)
        
    ElseIf elt1.Type = "Point" Then
        Set ref1 = elt1.Reference
        On Error Resume Next

        Set TheMeasurable = TheSPAWorkbench.GetMeasurable(ref1)
        Set vTheMeasurable = TheMeasurable
        vTheMeasurable.GetPoint acoord_in_part
        
    End If
        
    Label_pt_debut.Caption = "Point sélectionné (click click click)"
    'USelection.Item(1).Value.Parent.Parent.Name & "_" & USelection.Item(1).Value.Name
    End If
    
Call Creation_pt_debut(x, y, z)
USelection.Clear



'Tous les champs doivent être remplis
is_pt_debut_selected = True
'If is_pt_debut_selected *...*... Then
'Inserer fonction a executer
'End If

End Sub
Public Sub Creation_pt_debut(x As Double, y As Double, z As Double)

Dim hybridShapePointCoord1 As HybridShapePointCoord
Set hybridShapePointCoord1 = HSF.AddNewPointCoord(x, y, z)


'Insère le point dans la part créée et met a jour cette part.
B1.InsertHybridShape hybridShapePointCoord1
my_part.Update

'Juste pour vérifier que le code compile jusqu'au bout
Fenetre_Selection.Show



End Sub

Private Sub UserForm_Click()

End Sub

Attribute VB_Name = "Generation_chapes"
Sub CATMain()

End Sub

Attribute VB_Name = "Module1"
Sub CATMain()

Dim documents1 As Documents
Set documents1 = CATIA.Documents

Dim partDocument1 As PartDocument
Set partDocument1 = documents1.Item("Part_crashtest.CATPart")

Dim part1 As Part
Set part1 = partDocument1.Part

Dim bodies1 As Bodies
Set bodies1 = part1.Bodies

Dim body1 As Body
Set body1 = bodies1.Item("Corps principal")

Dim sketches1 As Sketches
Set sketches1 = body1.Sketches

Dim reference1 As Reference
Set reference1 = part1.CreateReferenceFromName("Selection_RSur:(Face:(Brp:(Shaft.1;0:(Brp:(Sketch.2;3)));None:();Cf11:());Shaft.1_ResultOUT;Z0;G3173)")

Dim sketch1 As Sketch
Set sketch1 = sketches1.Add(reference1)

Dim arrayOfVariantOfDouble1(8)
arrayOfVariantOfDouble1(0) = 0#
arrayOfVariantOfDouble1(1) = 120#
arrayOfVariantOfDouble1(2) = 0#
arrayOfVariantOfDouble1(3) = -1#
arrayOfVariantOfDouble1(4) = -0#
arrayOfVariantOfDouble1(5) = 0#
arrayOfVariantOfDouble1(6) = 0#
arrayOfVariantOfDouble1(7) = 0#
arrayOfVariantOfDouble1(8) = 1#
Set sketch1Variant = sketch1
sketch1Variant.SetAbsoluteAxisData arrayOfVariantOfDouble1

part1.InWorkObject = sketch1

Dim factory2D1 As Factory2D
Set factory2D1 = sketch1.OpenEdition()

Dim geometricElements1 As GeometricElements
Set geometricElements1 = sketch1.GeometricElements

Dim axis2D1 As Axis2D
Set axis2D1 = geometricElements1.Item("Repère")

Dim line2D1 As Line2D
Set line2D1 = axis2D1.GetItem("Axe horizontal")

line2D1.ReportName = 1

Dim line2D2 As Line2D
Set line2D2 = axis2D1.GetItem("Axe vertical")

line2D2.ReportName = 2

Dim point2D1 As Point2D
Set point2D1 = factory2D1.CreatePoint(0#, 0#)

point2D1.ReportName = 3

Dim circle2D1 As Circle2D
Set circle2D1 = factory2D1.CreateClosedCircle(0#, 0#, 9#)

circle2D1.CenterPoint = point2D1

circle2D1.ReportName = 4

Dim hybridShapes1 As HybridShapes
Set hybridShapes1 = body1.HybridShapes

Dim reference2 As Reference
Set reference2 = hybridShapes1.Item("Point_debut")

Dim geometricElements2 As GeometricElements
Set geometricElements2 = factory2D1.CreateProjections(reference2)

Dim geometry2D1 As Geometry2D
Set geometry2D1 = geometricElements2.Item("Empreinte.1")

geometry2D1.Construction = True

Dim constraints1 As Constraints
Set constraints1 = sketch1.Constraints

Dim reference3 As Reference
Set reference3 = part1.CreateReferenceFromObject(point2D1)

Dim reference4 As Reference
Set reference4 = part1.CreateReferenceFromObject(geometry2D1)

Dim constraint1 As Constraint
Set constraint1 = constraints1.AddBiEltCst(catCstTypeOn, reference3, reference4)

constraint1.Mode = catCstModeDrivingDimension

Dim reference5 As Reference
Set reference5 = part1.CreateReferenceFromObject(circle2D1)

Dim constraint2 As Constraint
Set constraint2 = constraints1.AddMonoEltCst(catCstTypeRadius, reference5)

constraint2.Mode = catCstModeDrivingDimension

Dim length1 As Length
Set length1 = constraint2.Dimension

length1.Value = 9#

sketch1.CloseEdition

part1.InWorkObject = sketch1

part1.UpdateObject sketch1

End Sub

Attribute VB_Name = "Module2"
Sub CATMain()

Dim documents1 As Documents
Set documents1 = CATIA.Documents

Dim partDocument1 As PartDocument
Set partDocument1 = documents1.Item("Part_crashtest.CATPart")

Dim part1 As Part
Set part1 = partDocument1.Part

Dim hybridShapeFactory1 As HybridShapeFactory
Set hybridShapeFactory1 = part1.HybridShapeFactory

Dim bodies1 As Bodies
Set bodies1 = part1.Bodies

Dim body1 As Body
Set body1 = bodies1.Item("Corps principal")

Dim hybridShapes1 As HybridShapes
Set hybridShapes1 = body1.HybridShapes

Dim hybridShapePointCenter1 As HybridShapePointCenter
Set hybridShapePointCenter1 = hybridShapes1.Item("Point_debut")

Dim reference1 As Reference
Set reference1 = part1.CreateReferenceFromObject(hybridShapePointCenter1)

Dim hybridShapePointCenter2 As HybridShapePointCenter
Set hybridShapePointCenter2 = hybridShapes1.Item("Point_fin")

Dim reference2 As Reference
Set reference2 = part1.CreateReferenceFromObject(hybridShapePointCenter2)

Dim hybridShapeLinePtPt1 As HybridShapeLinePtPt
Set hybridShapeLinePtPt1 = hybridShapeFactory1.AddNewLinePtPt(reference1, reference2)

body1.InsertHybridShape hybridShapeLinePtPt1

part1.InWorkObject = hybridShapeLinePtPt1

part1.Update

Dim reference3 As Reference
Set reference3 = part1.CreateReferenceFromObject(hybridShapeLinePtPt1)

Dim reference4 As Reference
Set reference4 = part1.CreateReferenceFromObject(hybridShapePointCenter2)

Dim hybridShapePlaneNormal1 As HybridShapePlaneNormal
Set hybridShapePlaneNormal1 = hybridShapeFactory1.AddNewPlaneNormal(reference3, reference4)

body1.InsertHybridShape hybridShapePlaneNormal1

part1.InWorkObject = hybridShapePlaneNormal1

part1.Update

End Sub

Attribute VB_Name = "Module3"
Sub CATMain()

Dim documents1 As Documents
Set documents1 = CATIA.Documents

Dim partDocument1 As PartDocument
Set partDocument1 = documents1.Item("Part_crashtest.CATPart")

Dim part1 As Part
Set part1 = partDocument1.Part

Dim hybridShapeFactory1 As HybridShapeFactory
Set hybridShapeFactory1 = part1.HybridShapeFactory

Dim bodies1 As Bodies
Set bodies1 = part1.Bodies

Dim body1 As Body
Set body1 = bodies1.Item("Corps principal")

Dim hybridShapes1 As HybridShapes
Set hybridShapes1 = body1.HybridShapes

Dim hybridShapeLinePtPt1 As HybridShapeLinePtPt
Set hybridShapeLinePtPt1 = hybridShapes1.Item("Droite.1")

Dim reference1 As Reference
Set reference1 = part1.CreateReferenceFromObject(hybridShapeLinePtPt1)

Dim hybridShapePlaneNormal1 As HybridShapePlaneNormal
Set hybridShapePlaneNormal1 = hybridShapeFactory1.AddNewPlaneNormal(reference1, Nothing)

body1.InsertHybridShape hybridShapePlaneNormal1

part1.InWorkObject = hybridShapePlaneNormal1

part1.Update

End Sub

Attribute VB_Name = "Module4"
Sub CATMain()

Dim documents1 As Documents
Set documents1 = CATIA.Documents

Dim partDocument1 As PartDocument
Set partDocument1 = documents1.Item("Part_crashtest.CATPart")

Dim part1 As Part
Set part1 = partDocument1.Part

Dim bodies1 As Bodies
Set bodies1 = part1.Bodies

Dim body1 As Body
Set body1 = bodies1.Item("Corps principal")

Dim sketches1 As Sketches
Set sketches1 = body1.Sketches

Dim hybridShapes1 As HybridShapes
Set hybridShapes1 = body1.HybridShapes

Dim reference1 As Reference
Set reference1 = hybridShapes1.Item("Plan.3")

Dim sketch1 As Sketch
Set sketch1 = sketches1.Add(reference1)

Dim arrayOfVariantOfDouble1(8)
arrayOfVariantOfDouble1(0) = 0#
arrayOfVariantOfDouble1(1) = 50#
arrayOfVariantOfDouble1(2) = 0#
arrayOfVariantOfDouble1(3) = -1#
arrayOfVariantOfDouble1(4) = 0#
arrayOfVariantOfDouble1(5) = 0#
arrayOfVariantOfDouble1(6) = 0#
arrayOfVariantOfDouble1(7) = -0#
arrayOfVariantOfDouble1(8) = 1#
Set sketch1Variant = sketch1
sketch1Variant.SetAbsoluteAxisData arrayOfVariantOfDouble1

part1.InWorkObject = sketch1

Dim factory2D1 As Factory2D
Set factory2D1 = sketch1.OpenEdition() 'edition de l'esquisse

'Dim geometricElements1 As GeometricElements
'Set geometricElements1 = sketch1.GeometricElements

'Dim axis2D1 As Axis2D
'Set axis2D1 = geometricElements1.Item("Repère")

'Dim line2D1 As Line2D
'Set line2D1 = axis2D1.GetItem("Axe horizontal")

'line2D1.ReportName = 1

'Dim line2D2 As Line2D
'Set line2D2 = axis2D1.GetItem("Axe vertical")

'line2D2.ReportName = 2

'Dim reference2 As Reference
'Set reference2 = hybridShapes1.Item("Droite.1")

Dim geometricElements2 As GeometricElements
Set geometricElements2 = factory2D1.CreateIntersections(reference2) 'La droite entre les deux points

'Dim geometry2D1 As Geometry2D
'Set geometry2D1 = geometricElements2.Item("Empreinte.1")

geometry2D1.Construction = True 'definir element de construction

Dim point2D1 As Point2D
Set point2D1 = factory2D1.CreatePoint(-49.913818, 0#) 'point de départ ligne

point2D1.ReportName = 3

Dim line2D3 As Line2D
Set line2D3 = factory2D1.CreateLine(-49.913818, 0#, 0#, 0#)

line2D3.ReportName = 4

line2D3.Construction = True

line2D3.StartPoint = point2D1 'declaration du point d'origine

Dim point2D2 As Point2D
Set point2D2 = axis2D1.GetItem("Origine") 'point de fin ligne

line2D3.EndPoint = point2D2 'declaration du point de fin

Dim constraints1 As Constraints
Set constraints1 = sketch1.Constraints 'contraintes de l'esquisse

Dim reference3 As Reference
Set reference3 = part1.CreateReferenceFromObject(point2D1)

Dim reference4 As Reference
Set reference4 = part1.CreateReferenceFromObject(line2D1)

Dim constraint1 As Constraint
Set constraint1 = constraints1.AddBiEltCst(catCstTypeOn, reference3, reference4)

constraint1.Mode = catCstModeDrivingDimension

Dim reference5 As Reference
Set reference5 = part1.CreateReferenceFromObject(line2D3)

Dim reference6 As Reference
Set reference6 = part1.CreateReferenceFromObject(line2D1)

Dim constraint2 As Constraint
Set constraint2 = constraints1.AddBiEltCst(catCstTypeHorizontality, reference5, reference6) 'entre l'axe horizontal et la droite

constraint2.Mode = catCstModeDrivingDimension 'je sais pas a quoi ça sert

Dim point2D3 As Point2D
Set point2D3 = factory2D1.CreatePoint(-51.097316, 7.924386)

point2D3.ReportName = 5

Dim point2D4 As Point2D
Set point2D4 = factory2D1.CreatePoint(0#, 15#)

point2D4.ReportName = 6

Dim line2D4 As Line2D
Set line2D4 = factory2D1.CreateLine(-51.097316, 7.924386, 0#, 15#) 'ligne entre deux points

line2D4.ReportName = 7

line2D4.StartPoint = point2D3 'point de début

line2D4.EndPoint = point2D4 'point de fin

Dim point2D5 As Point2D
Set point2D5 = factory2D1.CreatePoint(-51.097316, -7.924386)

point2D5.ReportName = 8

Dim point2D6 As Point2D
Set point2D6 = factory2D1.CreatePoint(0#, -15#)

point2D6.ReportName = 9

Dim line2D5 As Line2D
Set line2D5 = factory2D1.CreateLine(-51.097316, -7.924386, 0#, -15#) 'ligne entre deux points

line2D5.ReportName = 10

line2D5.StartPoint = point2D5 'point de début

line2D5.EndPoint = point2D6 'point de fin

Dim reference7 As Reference
Set reference7 = part1.CreateReferenceFromObject(line2D5)

Dim reference8 As Reference
Set reference8 = part1.CreateReferenceFromObject(line2D4)

Dim reference9 As Reference
Set reference9 = part1.CreateReferenceFromObject(line2D3)

Dim constraint3 As Constraint
Set constraint3 = constraints1.AddTriEltCst(catCstTypeSymmetry, reference7, reference8, reference9) 'symetrie entre les deux droites par raport à la droite d'origine

constraint3.Mode = catCstModeDrivingDimension

Dim reference10 As Reference
Set reference10 = part1.CreateReferenceFromObject(point2D3)

Dim reference11 As Reference
Set reference11 = part1.CreateReferenceFromObject(point2D5)

Dim reference12 As Reference
Set reference12 = part1.CreateReferenceFromObject(line2D3)

Dim constraint4 As Constraint
Set constraint4 = constraints1.AddTriEltCst(catCstTypeSymmetry, reference10, reference11, reference12) 'symetrie entre deux points par rapport à la droite

constraint4.Mode = catCstModeDrivingDimension

Dim reference13 As Reference
Set reference13 = part1.CreateReferenceFromObject(point2D6)

Dim reference14 As Reference
Set reference14 = part1.CreateReferenceFromObject(point2D4)

Dim reference15 As Reference
Set reference15 = part1.CreateReferenceFromObject(line2D3)

Dim constraint5 As Constraint
Set constraint5 = constraints1.AddTriEltCst(catCstTypeSymmetry, reference13, reference14, reference15) 'symetrie entre deux points par rapport à la droite

constraint5.Mode = catCstModeDrivingDimension

Dim point2D7 As Point2D
Set point2D7 = factory2D1.CreatePoint(-50#, 0#) 'point de centre du cercle

point2D7.ReportName = 11

Dim circle2D1 As Circle2D
Set circle2D1 = factory2D1.CreateCircle(-50#, 0#, 8#, 1.708395, 4.574791) 'creation du cercle

circle2D1.CenterPoint = point2D7 'centre

circle2D1.ReportName = 12

circle2D1.EndPoint = point2D5 'point 1

circle2D1.StartPoint = point2D3 'point 2

Dim reference16 As Reference
Set reference16 = part1.CreateReferenceFromObject(circle2D1)

Dim reference17 As Reference
Set reference17 = part1.CreateReferenceFromObject(line2D4)

Dim constraint6 As Constraint
Set constraint6 = constraints1.AddBiEltCst(catCstTypeTangency, reference16, reference17) 'tangence avec la droite en biais

constraint6.Mode = catCstModeDrivingDimension

Dim line2D6 As Line2D
Set line2D6 = factory2D1.CreateLine(0#, 15#, 0#, -15#) 'creation ligne au hasard

line2D6.ReportName = 13

line2D6.StartPoint = point2D4 'point debut

line2D6.EndPoint = point2D6 'point fin

Dim reference18 As Reference
Set reference18 = part1.CreateReferenceFromObject(line2D6)

Dim reference19 As Reference
Set reference19 = part1.CreateReferenceFromObject(line2D2)

Dim constraint7 As Constraint
Set constraint7 = constraints1.AddBiEltCst(catCstTypeVerticality, reference18, reference19) 'inutile je pense, je ne me suis pas géré

constraint7.Mode = catCstModeDrivingDimension

Dim reference20 As Reference
Set reference20 = hybridShapes1.Item("Point_debut")

Dim geometricElements3 As GeometricElements
Set geometricElements3 = factory2D1.CreateProjections(reference20) 'projection d'un des points

Dim geometry2D2 As Geometry2D
Set geometry2D2 = geometricElements3.Item("Empreinte.1")

geometry2D2.Construction = True

Dim reference21 As Reference
Set reference21 = part1.CreateReferenceFromObject(line2D6)

Dim reference22 As Reference
Set reference22 = part1.CreateReferenceFromObject(geometry2D2)

Dim constraint8 As Constraint
Set constraint8 = constraints1.AddBiEltCst(catCstTypeDistance, reference21, reference22)

constraint8.Mode = catCstModeDrivingDimension

Dim length1 As Length
Set length1 = constraint8.Dimension

length1.Value = 0# ' on fixe la coincidence

Dim point2D8 As Point2D
Set point2D8 = factory2D1.CreatePoint(-50#, 0#)

point2D8.ReportName = 14

Dim circle2D2 As Circle2D
Set circle2D2 = factory2D1.CreateClosedCircle(-50#, 0#, 3#) 'creation du trou

circle2D2.CenterPoint = point2D8 'centre du cercle

circle2D2.ReportName = 15

Dim reference23 As Reference
Set reference23 = hybridShapes1.Item("Point.3")

Dim geometricElements4 As GeometricElements
Set geometricElements4 = factory2D1.CreateProjections(reference23)

Dim geometry2D3 As Geometry2D
Set geometry2D3 = geometricElements4.Item("Empreinte.1")

geometry2D3.Construction = True

Dim reference24 As Reference
Set reference24 = part1.CreateReferenceFromObject(point2D8)

Dim reference25 As Reference
Set reference25 = part1.CreateReferenceFromObject(geometry2D3)

Dim constraint9 As Constraint
Set constraint9 = constraints1.AddBiEltCst(catCstTypeOn, reference24, reference25)

constraint9.Mode = catCstModeDrivingDimension

Dim reference26 As Reference
Set reference26 = part1.CreateReferenceFromObject(circle2D1)

Dim constraint10 As Constraint
Set constraint10 = constraints1.AddMonoEltCst(catCstTypeRadius, reference26) 'rayon du cercle

constraint10.Mode = catCstModeDrivingDimension

Dim length2 As Length
Set length2 = constraint10.Dimension

length2.Value = 8# 'valeur de la contrainte de rayon

Dim reference27 As Reference
Set reference27 = part1.CreateReferenceFromObject(circle2D2)

Dim constraint11 As Constraint
Set constraint11 = constraints1.AddMonoEltCst(catCstTypeRadius, reference27) 'rayon du trou

constraint11.Mode = catCstModeDrivingDimension

Dim length3 As Length
Set length3 = constraint11.Dimension

length3.Value = 3# 'valeur de la contrainte

Dim reference28 As Reference
Set reference28 = part1.CreateReferenceFromObject(line2D6)

Dim constraint12 As Constraint
Set constraint12 = constraints1.AddMonoEltCst(catCstTypeLength, reference28) 'contrainte pour la largeur en bout de chape (cf diametre tube je pense)

constraint12.Mode = catCstModeDrivingDimension

Dim length4 As Length
Set length4 = constraint12.Dimension

length4.Value = 30# 'valeur de la contrainte

Dim geometricElements5 As GeometricElements
Set geometricElements5 = factory2D1.CreateProjections(reference23)

Dim geometry2D4 As Geometry2D
Set geometry2D4 = geometricElements5.Item("Empreinte.1")

geometry2D4.Construction = True

Dim reference29 As Reference
Set reference29 = part1.CreateReferenceFromObject(point2D7)

Dim reference30 As Reference
Set reference30 = part1.CreateReferenceFromObject(geometry2D4)

Dim constraint13 As Constraint
Set constraint13 = constraints1.AddBiEltCst(catCstTypeOn, reference29, reference30) 'contrainte en bout de chape

constraint13.Mode = catCstModeDrivingDimension

sketch1.CloseEdition

part1.InWorkObject = sketch1

part1.UpdateObject sketch1

End Sub

Attribute VB_Name = "Module5"
Sub CATMain()
 ' a garder selon moi
 

Dim factory2D1 As Factory2D
Set factory2D1 = sketch1.OpenEdition() 'edition de l'esquisse

Dim geometricElements1 As GeometricElements
Set geometricElements1 = sketch1.GeometricElements

Dim axis2D1 As Axis2D
Set axis2D1 = geometricElements1.Item("Repère")

Dim line2D1 As Line2D
Set line2D1 = axis2D1.GetItem("Axe horizontal")

Dim geometricElements2 As GeometricElements
Set geometricElements2 = factory2D1.CreateIntersections(Axe_Tube) 'La droite entre les deux points


'Dim geometry2D1 As Geometry2D
'Set geometry2D1 = geometricElements2.Item("Empreinte.1")

geometry2D1.Construction = True 'definir element de construction

Dim point_rotule As GeometricElements
Set point_rotule = factory2D1.CreateProjections(point_rotule)


Dim point2D1 As Point2D
Set point2D1 = factory2D1.CreatePoint(-49.913818, 0#) 'point de départ ligne


Dim line_symetry As Line2D
Set line_symetry = factory2D1.CreateLine(-49.913818, 0#, 0#, 0#)

'line2D3.ReportName = 4

line_symetry.Construction = True

line_symetry.StartPoint = point2D1 'declaration du point d'origine

Dim point2D2 As Point2D
Set point2D2 = axis2D1.GetItem("Origine") 'point de fin ligne

line_symetry.EndPoint = point2D2 'declaration du point de fin

Dim constraints1 As Constraints
Set constraints1 = sketch1.Constraints 'contraintes de l'esquisse

Dim reference3 As Reference
Set reference3 = part1.CreateReferenceFromObject(point2D1)

Dim reference4 As Reference
Set reference4 = part1.CreateReferenceFromObject(line2D1)

Dim constraint1 As Constraint
Set constraint1 = constraints1.AddBiEltCst(catCstTypeOn, reference3, reference4)

constraint1.Mode = catCstModeDrivingDimension

Dim reference5 As Reference
Set reference5 = part1.CreateReferenceFromObject(line_symetry)

Dim reference6 As Reference
Set reference6 = part1.CreateReferenceFromObject(line2D1)

Dim constraint2 As Constraint
Set constraint2 = constraints1.AddBiEltCst(catCstTypeHorizontality, reference5, reference6) 'entre l'axe horizontal et la droite

'-------------------------------------------
constraint2.Mode = catCstModeDrivingDimension 'je sais pas a quoi ça sert

Dim point2D3 As Point2D
Set point2D3 = factory2D1.CreatePoint(-51.097316, 7.924386)

point2D3.ReportName = 5

Dim point2D4 As Point2D
Set point2D4 = factory2D1.CreatePoint(0#, 15#)

point2D4.ReportName = 6

Dim line2D4 As Line2D
Set line2D4 = factory2D1.CreateLine(-51.097316, 7.924386, 0#, 15#) 'ligne entre deux points

line2D4.ReportName = 7

line2D4.StartPoint = point2D3 'point de début

line2D4.EndPoint = point2D4 'point de fin

Dim point2D5 As Point2D
Set point2D5 = factory2D1.CreatePoint(-51.097316, -7.924386)

point2D5.ReportName = 8

Dim point2D6 As Point2D
Set point2D6 = factory2D1.CreatePoint(0#, -15#)

point2D6.ReportName = 9

Dim line2D5 As Line2D
Set line2D5 = factory2D1.CreateLine(-51.097316, -7.924386, 0#, -15#) 'ligne entre deux points

line2D5.ReportName = 10

line2D5.StartPoint = point2D5 'point de début

line2D5.EndPoint = point2D6 'point de fin

Dim reference7 As Reference
Set reference7 = part1.CreateReferenceFromObject(line2D5)

Dim reference8 As Reference
Set reference8 = part1.CreateReferenceFromObject(line2D4)

Dim reference9 As Reference
Set reference9 = part1.CreateReferenceFromObject(line_symetry)

Dim constraint3 As Constraint
Set constraint3 = constraints1.AddTriEltCst(catCstTypeSymmetry, reference7, reference8, reference9) 'symetrie entre les deux droites par raport à la droite d'origine

constraint3.Mode = catCstModeDrivingDimension

Dim reference10 As Reference
Set reference10 = part1.CreateReferenceFromObject(point2D3)

Dim reference11 As Reference
Set reference11 = part1.CreateReferenceFromObject(point2D5)

Dim reference12 As Reference
Set reference12 = part1.CreateReferenceFromObject(line_symetry)

Dim constraint4 As Constraint
Set constraint4 = constraints1.AddTriEltCst(catCstTypeSymmetry, reference10, reference11, reference12) 'symetrie entre deux points par rapport à la droite

constraint4.Mode = catCstModeDrivingDimension

Dim reference13 As Reference
Set reference13 = part1.CreateReferenceFromObject(point2D6)

Dim reference14 As Reference
Set reference14 = part1.CreateReferenceFromObject(point2D4)

Dim reference15 As Reference
Set reference15 = part1.CreateReferenceFromObject(line_symetry)

Dim constraint5 As Constraint
Set constraint5 = constraints1.AddTriEltCst(catCstTypeSymmetry, reference13, reference14, reference15) 'symetrie entre deux points par rapport à la droite

constraint5.Mode = catCstModeDrivingDimension

Dim point2D7 As Point2D
Set point2D7 = factory2D1.CreatePoint(-50#, 0#) 'point de centre du cercle

point2D7.ReportName = 11

Dim circle2D1 As Circle2D
Set circle2D1 = factory2D1.CreateCircle(-50#, 0#, 8#, 1.708395, 4.574791) 'creation du cercle

circle2D1.CenterPoint = point2D7 'centre

circle2D1.ReportName = 12

circle2D1.EndPoint = point2D5 'point 1

circle2D1.StartPoint = point2D3 'point 2

Dim reference16 As Reference
Set reference16 = part1.CreateReferenceFromObject(circle2D1)

Dim reference17 As Reference
Set reference17 = part1.CreateReferenceFromObject(line2D4)

Dim constraint6 As Constraint
Set constraint6 = constraints1.AddBiEltCst(catCstTypeTangency, reference16, reference17) 'tangence avec la droite en biais

constraint6.Mode = catCstModeDrivingDimension

Dim line2D6 As Line2D
Set line2D6 = factory2D1.CreateLine(0#, 15#, 0#, -15#) 'creation ligne au hasard

line2D6.ReportName = 13

line2D6.StartPoint = point2D4 'point debut

line2D6.EndPoint = point2D6 'point fin

Dim reference18 As Reference
Set reference18 = part1.CreateReferenceFromObject(line2D6)

Dim reference19 As Reference
Set reference19 = part1.CreateReferenceFromObject(line2D2)

Dim constraint7 As Constraint
Set constraint7 = constraints1.AddBiEltCst(catCstTypeVerticality, reference18, reference19) 'inutile je pense, je ne me suis pas géré

constraint7.Mode = catCstModeDrivingDimension

Dim reference20 As Reference
Set reference20 = hybridShapes1.Item("Point_debut")

Dim geometricElements3 As GeometricElements
Set geometricElements3 = factory2D1.CreateProjections(reference20) 'projection d'un des points

Dim geometry2D2 As Geometry2D
Set geometry2D2 = geometricElements3.Item("Empreinte.1")

geometry2D2.Construction = True

Dim reference21 As Reference
Set reference21 = part1.CreateReferenceFromObject(line2D6)

Dim reference22 As Reference
Set reference22 = part1.CreateReferenceFromObject(geometry2D2)

Dim constraint8 As Constraint
Set constraint8 = constraints1.AddBiEltCst(catCstTypeDistance, reference21, reference22)

constraint8.Mode = catCstModeDrivingDimension

Dim length1 As Length
Set length1 = constraint8.Dimension

length1.Value = 0# ' on fixe la coincidence

Dim point2D8 As Point2D
Set point2D8 = factory2D1.CreatePoint(-50#, 0#)

point2D8.ReportName = 14

Dim circle2D2 As Circle2D
Set circle2D2 = factory2D1.CreateClosedCircle(-50#, 0#, 3#) 'creation du trou

circle2D2.CenterPoint = point2D8 'centre du cercle

circle2D2.ReportName = 15

Dim reference23 As Reference
Set reference23 = hybridShapes1.Item("Point.3")

Dim geometricElements4 As GeometricElements
Set geometricElements4 = factory2D1.CreateProjections(reference23)

Dim geometry2D3 As Geometry2D
Set geometry2D3 = geometricElements4.Item("Empreinte.1")

geometry2D3.Construction = True

Dim reference24 As Reference
Set reference24 = part1.CreateReferenceFromObject(point2D8)

Dim reference25 As Reference
Set reference25 = part1.CreateReferenceFromObject(geometry2D3)

Dim constraint9 As Constraint
Set constraint9 = constraints1.AddBiEltCst(catCstTypeOn, reference24, reference25)

constraint9.Mode = catCstModeDrivingDimension

Dim reference26 As Reference
Set reference26 = part1.CreateReferenceFromObject(circle2D1)

Dim constraint10 As Constraint
Set constraint10 = constraints1.AddMonoEltCst(catCstTypeRadius, reference26) 'rayon du cercle

constraint10.Mode = catCstModeDrivingDimension

Dim length2 As Length
Set length2 = constraint10.Dimension

length2.Value = 8# 'valeur de la contrainte de rayon

Dim reference27 As Reference
Set reference27 = part1.CreateReferenceFromObject(circle2D2)

Dim constraint11 As Constraint
Set constraint11 = constraints1.AddMonoEltCst(catCstTypeRadius, reference27) 'rayon du trou

constraint11.Mode = catCstModeDrivingDimension

Dim length3 As Length
Set length3 = constraint11.Dimension

length3.Value = 3# 'valeur de la contrainte

Dim reference28 As Reference
Set reference28 = part1.CreateReferenceFromObject(line2D6)

Dim constraint12 As Constraint
Set constraint12 = constraints1.AddMonoEltCst(catCstTypeLength, reference28) 'contrainte pour la largeur en bout de chape (cf diametre tube je pense)

constraint12.Mode = catCstModeDrivingDimension

Dim length4 As Length
Set length4 = constraint12.Dimension

length4.Value = 30# 'valeur de la contrainte

Dim geometricElements5 As GeometricElements
Set geometricElements5 = factory2D1.CreateProjections(reference23)

Dim geometry2D4 As Geometry2D
Set geometry2D4 = geometricElements5.Item("Empreinte.1")

geometry2D4.Construction = True

Dim reference29 As Reference
Set reference29 = part1.CreateReferenceFromObject(point2D7)

Dim reference30 As Reference
Set reference30 = part1.CreateReferenceFromObject(geometry2D4)

Dim constraint13 As Constraint
Set constraint13 = constraints1.AddBiEltCst(catCstTypeOn, reference29, reference30) 'contrainte en bout de chape

constraint13.Mode = catCstModeDrivingDimension

sketch1.CloseEdition

part1.InWorkObject = sketch1

part1.UpdateObject sketch1

End Sub

Attribute VB_Name = "Module_variables"
' --------------------------------------
' Création des variables globales
' --------------------------------------

Public RootDoc As Document
Public RootProduct As Product
Public AllProds As Products

Public Mon_Prod As Product
Public AllDocs As Documents
Public Docpart1 As PartDocument
Public my_part As Part

Public HSF As HybridShapeFactory
Public Listbodies As Bodies
Public B1 As Body

Public my_shapes As HybridShapes

' Variables de l'emplacement des élements de référence
Public pt_debut_ref As Reference
Public is_pt_debut_selected As Boolean

Attribute VB_Name = "test"
Sub CATMain()

Dim documents1 As Documents
Set documents1 = CATIA.Documents

Dim partDocument1 As PartDocument
Set partDocument1 = documents1.Item("Part3.CATPart")

Dim part1 As Part
Set part1 = partDocument1.Part

Dim hybridShapeFactory1 As HybridShapeFactory
Set hybridShapeFactory1 = part1.HybridShapeFactory

Dim hybridShapePointCoord1 As HybridShapePointCoord
Set hybridShapePointCoord1 = hybridShapeFactory1.AddNewPointCoord(0#, 0#, 0#)

Dim axisSystems1 As AxisSystems
Set axisSystems1 = part1.AxisSystems

Dim axisSystem1 As AxisSystem
Set axisSystem1 = axisSystems1.Item("Repère absolu")

Dim reference1 As Reference
Set reference1 = part1.CreateReferenceFromObject(axisSystem1)

hybridShapePointCoord1.RefAxisSystem = reference1

Dim bodies1 As Bodies
Set bodies1 = part1.Bodies

Dim body1 As Body
Set body1 = bodies1.Item("Corps principal")

body1.InsertHybridShape hybridShapePointCoord1

part1.InWorkObject = hybridShapePointCoord1

part1.Update

End Sub
