Attribute VB_Name = "Fenetre_Selection"
Attribute VB_Base = "0{5CA61013-9B89-465D-BE29-C309F1BA5F18}{39883149-D42C-411E-ABCD-0913F8118E43}"
Attribute VB_GlobalNameSpace = False
Attribute VB_Creatable = False
Attribute VB_PredeclaredId = True
Attribute VB_Exposed = False
Attribute VB_TemplateDerived = False
Attribute VB_Customizable = False
Private Sub Button_annuler_Click()
Fenetre_Selection.Hide
End Sub
Private Sub Button_chape_Click()


Call creation_chape(part_chape_1, HSF1, Listbodies1, B1, pt1_chape_1, Pt_debut_1, Pt_fin_1, pt1_chape_1, pt2_chape_1)
Call creation_chape(part_chape_2, HSF2, Listbodies2, B2, pt2_chape_2, Pt_debut_2, Pt_fin_2, pt1_chape_2, pt2_chape_2)

Fenetre_Selection.Hide

End Sub

Private Sub Button_pt_debut_Click()
Fenetre_Selection.Hide

' --------------------------------------------------------------------------------
' Selection du point de départ du tube (en vue de former l'axe du tube plus tard)
' --------------------------------------------------------------------------------
    
'Déclaration des variables
Dim USelection As Object
Dim InputObject(0)
Dim oStatus
Dim elt1, Coord(2), ref1
Dim X As Double, Y As Double, z As Double
InputObject(0) = "Vertex" 'c'est un filtre (le curseur ne selectionne que ça). Vertex = sommets d'une géo 3D
Set USelection = CATIA.ActiveDocument.Selection
USelection.Clear
    
'Sélectionner un élément
oStatus = USelection.SelectElement2(InputObject, "Selectionnez le point de départ du tube (type Vertex)", False)
If (oStatus = "Cancel") Then
    Exit Sub
Else
    Set elt1 = USelection.Item2(1)
    elt1.GetCoordinates Coord
        X = Coord(0)
        Y = Coord(1)
        z = Coord(2)
           
    Label_pt_debut1.Caption = "Point début sélectionné"
End If

' ----------------------------------------------------------
' Copie du point sélectionné dans les parts des chapes 1 et 2
' ----------------------------------------------------------
'Copie dans la part de la chape 1
Set Pt_debut_1 = HSF1.AddNewPointCoord(X, Y, z)
Pt_debut_1.Name = "Pt_debut"
B1.InsertHybridShape Pt_debut_1
part_chape_1.Update

'Copie dans la part de la chape 2
Set Pt_debut_2 = HSF2.AddNewPointCoord(X, Y, z)
Pt_debut_2.Name = "Pt_debut"
B2.InsertHybridShape Pt_debut_2
part_chape_2.Update

Fenetre_Selection.Show 'on rouvre la fenetre de selection pour les étapes suivantes
USelection.Clear
End Sub
Private Sub Button_pt_fin_Click()
Fenetre_Selection.Hide
' --------------------------------------------------------------------------------
' Selection du point de fin du tube (en vue de former l'axe du tube plus tard)
' --------------------------------------------------------------------------------

'Déclaration des variables
Dim USelection As Object
Dim InputObject(0)
Dim oStatus
Dim elt1, Coord(2), ref1
Dim X As Double, Y As Double, z As Double
InputObject(0) = "Vertex" 'c'est un filtre (le curseur ne selectionne que ça). Vertex = sommets d'une géo 3D
Set USelection = CATIA.ActiveDocument.Selection
USelection.Clear
    
'Sélectionner un élément
oStatus = USelection.SelectElement2(InputObject, "Selectionnez le point de départ du tube (type Vertex)", False)
If (oStatus = "Cancel") Then
    Exit Sub
Else
    Set elt1 = USelection.Item2(1)
    elt1.GetCoordinates Coord
        X = Coord(0)
        Y = Coord(1)
        z = Coord(2)
        
    Label_pt_fin.Caption = "Point fin sélectionné"
End If
    
' ----------------------------------------------------------
' Copie du point sélectionné dans les parts des chapes 1 et 2
' ----------------------------------------------------------
'Copie dans la part de la chape 1
Set Pt_fin_1 = HSF1.AddNewPointCoord(X, Y, z)
Pt_fin_1.Name = "Pt_fin"
B1.InsertHybridShape Pt_fin_1
part_chape_1.Update

'Copie dans la part de la chape 2
Set Pt_fin_2 = HSF2.AddNewPointCoord(X, Y, z)
Pt_fin_2.Name = "Pt_fin"
B2.InsertHybridShape Pt_fin_2
part_chape_2.Update

Fenetre_Selection.Show 'on rouvre la fenetre de selection pour les étapes suivantes
USelection.Clear
End Sub
Private Sub Button_pt_chape_1_Click()
Fenetre_Selection.Hide
' --------------------------------------------------------------------------------------
' Selection du point de fin du tube (en vue de former l'axe de la rotule tube plus tard)
' --------------------------------------------------------------------------------------

'Déclaration des variables
Dim USelection As Object
Dim InputObject(0)
Dim oStatus
Dim elt1, Coord(2), ref1
Dim X As Double, Y As Double, z As Double
InputObject(0) = "Vertex" 'c'est un filtre (le curseur ne selectionne que ça). Vertex = sommets d'une géo 3D
Set USelection = CATIA.ActiveDocument.Selection
USelection.Clear
    
'Sélectionner un élément
oStatus = USelection.SelectElement2(InputObject, "Selectionnez le point de départ du tube (type Vertex)", False)
If (oStatus = "Cancel") Then
    Exit Sub
Else
    Set elt1 = USelection.Item2(1)
    elt1.GetCoordinates Coord
        X = Coord(0)
        Y = Coord(1)
        z = Coord(2)
        
    Label_pt_chape_1.Caption = "Point Chape 1 sélectionné"
    
End If

' ----------------------------------------------------------
' Copie du point sélectionné dans les parts des chapes 1 et 2
' ----------------------------------------------------------
'Copie dans la part de la chape 1
Set pt1_chape_1 = HSF1.AddNewPointCoord(X, Y, z)
pt1_chape_1.Name = "Point Chape 1"
B1.InsertHybridShape pt1_chape_1
part_chape_1.Update

'Copie dans la part de la chape 2
Set pt1_chape_2 = HSF2.AddNewPointCoord(X, Y, z)
pt1_chape_2.Name = "Point Chape 1"
B2.InsertHybridShape pt1_chape_2
part_chape_2.Update

Fenetre_Selection.Show
USelection.Clear

End Sub
Private Sub Button_pt_chape_2_Click()
Fenetre_Selection.Hide
' --------------------------------------------------------------------------------------
' Selection du point de fin du tube (en vue de former l'axe de la rotule tube plus tard)
' --------------------------------------------------------------------------------------

'Déclaration des variables
Dim USelection As Object
Dim InputObject(0)
Dim oStatus
Dim elt1, Coord(2), ref1
Dim X As Double, Y As Double, z As Double
InputObject(0) = "Vertex" 'c'est un filtre (le curseur ne selectionne que ça). Vertex = sommets d'une géo 3D
Set USelection = CATIA.ActiveDocument.Selection
USelection.Clear
    
'Sélectionner un élément
oStatus = USelection.SelectElement2(InputObject, "Selectionnez le point de départ du tube (type Vertex)", False)
If (oStatus = "Cancel") Then
    Exit Sub
Else
    Set elt1 = USelection.Item2(1)
    elt1.GetCoordinates Coord
        X = Coord(0)
        Y = Coord(1)
        z = Coord(2)
        
    Label_pt_chape_2.Caption = "Point Chape 2 sélectionné"
    
End If

' ----------------------------------------------------------
' Copie du point sélectionné dans les parts des chapes 1 et 2
' ----------------------------------------------------------
'Copie dans la part de la chape 1
Set pt2_chape_1 = HSF1.AddNewPointCoord(X, Y, z)
pt2_chape_1.Name = "Point Chape 2"
B1.InsertHybridShape pt2_chape_1
part_chape_1.Update

'Copie dans la part de la chape 2
Set pt2_chape_2 = HSF2.AddNewPointCoord(X, Y, z)
pt2_chape_2.Name = "Point Chape 2"
B2.InsertHybridShape pt2_chape_2
part_chape_2.Update

Fenetre_Selection.Show
USelection.Clear



End Sub
Public Sub creation_chape(my_part As Part, HSF As HybridShapeFactory, ListBodies As Bodies, my_body As Body, pt_chape As HybridShapePointCoord, Pt_debut As HybridShapePointCoord, Pt_fin As HybridShapePointCoord, pt_chape_1 As HybridShapePointCoord, pt_chape_2 As HybridShapePointCoord)

' -----------------------------------------------------------------------
' Créations d'éléments géométriques de référence pour générer la chape.
' -----------------------------------------------------------------------

'Création droite représantant l'axe du tube
Dim Axe_Tube As HybridShapeLinePtPt
Set Axe_Tube = HSF.AddNewLinePtPt(Pt_debut, Pt_fin)
Axe_Tube.Name = "Axe Tube"
my_body.InsertHybridShape Axe_Tube
my_part.Update

'Création du plan normal à l'axe du tube (en vue de la création de la poche (plus tard))
Set Plan_normal_axe = HSF.AddNewPlaneNormal(Axe_Tube, Nothing)
Plan_normal_axe.Name = "Plan Poche"
my_body.InsertHybridShape Plan_normal_axe


'Création droite représantant l'axe de la rotule (pour ensuite faire  le plan d'esquisse de la chape (juste après))
Set Axe_Rotule = HSF.AddNewLinePtPt(pt_chape_1, pt_chape_2)
Axe_Rotule.Name = "Axe Rotule"
my_body.InsertHybridShape Axe_Rotule
my_part.Update

'Création du plan d'esquisse de la chape
Set Plan_chape = HSF.AddNewPlaneNormal(Axe_Rotule, pt_chape)
Plan_chape.Name = "Plan Chape"
my_body.InsertHybridShape Plan_chape

'Création de l'esquisse de la chape
Dim mes_esquisses As Sketches
Set mes_esquisses = my_body.Sketches
Dim mon_esquisse_chape  As Sketch
Dim factory2D_extrusion As Factory2D

'METTRE AILLEURS
Dim factory2D_poche As Factory2D
Dim ma_forme As Pad
Dim mon_esquisse_poche_1 As Sketch

' -----------------------------
' Esquisse du corps de la chape
' -----------------------------
'Positionnement de l'esquisse
Set mon_esquisse_chape = mes_esquisses.Add(Plan_chape)
my_part.InWorkObject = mon_esquisse_chape
Set factory2D_extrusion = mon_esquisse_chape.OpenEdition() 'Edition de l'esquisse

'Création du point d'intersection entre l'axe du tube et le plan d'esquisse de la chape
Dim geometricElements1 As GeometricElements
Set geometricElements1 = mon_esquisse_chape.GeometricElements
Dim axis2D1 As Axis2D
Set axis2D1 = geometricElements1.Item("Repère")
Dim line2D1 As Line2D
Set line2D1 = axis2D1.GetItem("Axe horizontal")
Dim geometricElements2 As GeometricElements
Set geometricElements2 = factory2D_extrusion.CreateIntersections(Axe_Tube) 'L'axe du tube
Dim inter_axe_tube As Geometry2D
Set inter_axe_tube = geometricElements2.Item("Empreinte.1")
inter_axe_tube.Construction = True 'definit element de construction


'_________________________________Début de la création de l'axe de symétrie de la chape_________________________________


'Création point de départ de l'axe
Dim centre_trou_1 As GeometricElements
Set centre_trou_1 = factory2D_extrusion.CreateProjections(pt_chape) 'Projection Point_chape_1 dans esquisse, c'est aussi le centre du trou de la chape
Dim centre_trou_geo_1 As Geometry2D
Set centre_trou_geo_1 = centre_trou_1.Item("Empreinte.1") 'transforme le point en type "Geometry2D" pour compatibilité plus tard
Dim centre_trou_2D As Point2D
Set centre_trou_2D = factory2D_extrusion.CreatePoint(-50, 0#) 'point de départ ligne, c'est un point de construction placé arbitrairement
centre_trou_2D.Construction = True
centre_trou_geo_1.Construction = True

'fait coincider point de départ de l'axe avec le centre du trou de la chape
Dim ref_centre_trou_2D As Reference
Set ref_centre_trou_2D = my_part.CreateReferenceFromObject(centre_trou_2D)
Dim ref_centre_trou As Reference
Set ref_centre_trou = my_part.CreateReferenceFromObject(centre_trou_geo_1)
Dim constraints1 As Constraints
Set constraints1 = mon_esquisse_chape.Constraints
Dim constraint1 As Constraint
Set constraint1 = constraints1.AddBiEltCst(catCstTypeOn, ref_centre_trou_2D, ref_centre_trou)

'Création point de fin de l'axe
Dim inter_axe_tube_2D As Point2D
Set inter_axe_tube_2D = factory2D_extrusion.CreatePoint(50, 0#)  'point de fin ligne, placé arbitrairement

'fait coincider point construction de l'axe de symétrie avec le point d'intersection entre plan d'esquisse et axe tube (généré plus haut)
Dim ref_inter_axe_tube_2D As Reference
Set ref_inter_axe_tube_2D = my_part.CreateReferenceFromObject(inter_axe_tube_2D)
Dim ref_inter_axe_tube As Reference
Set ref_inter_axe_tube = my_part.CreateReferenceFromObject(inter_axe_tube)
Dim constraint2 As Constraint
Set constraint2 = constraints1.AddBiEltCst(catCstTypeOn, ref_inter_axe_tube_2D, ref_inter_axe_tube)

Dim line_symetry As Line2D
Set line_symetry = factory2D_extrusion.CreateLine(-50, 0#, 0#, 0#) ' Création axe de symétrie de la chape de façon arbitraire
line_symetry.Construction = True
line_symetry.StartPoint = centre_trou_2D 'declaration du point d'origine (c'est un point de construction)
line_symetry.EndPoint = inter_axe_tube_2D 'declaration du point de fin de la ligne (c'est un point de construction)


'_________________________________Fin de la création de l'axe de symétrie de la chape_________________________________


'_________________________________Début création droites structure chape (on les créé à partir de 2 points chacune)_________________________________

'Génération des 4 points nécessaires de façon arbitraire (ils seront placé correctement par la suite)
Dim point2D1 As Point2D
Set point2D1 = factory2D_extrusion.CreatePoint(0, 10)
Dim point2D2 As Point2D
Set point2D2 = factory2D_extrusion.CreatePoint(10#, 10#)
Dim point2D3 As Point2D
Set point2D3 = factory2D_extrusion.CreatePoint(0, -10)
Dim point2D4 As Point2D
Set point2D4 = factory2D_extrusion.CreatePoint(10#, -10#)

'génère la première droite entre deux points
Dim line2D2 As Line2D
Set line2D2 = factory2D_extrusion.CreateLine(0, 1, 1#, 1#)
line2D2.StartPoint = point2D1 'point de début
line2D2.EndPoint = point2D2 'point de fin

'génère la seconde droite entre deux points
Dim line2D3 As Line2D
Set line2D3 = factory2D_extrusion.CreateLine(0, -1, 1#, -1#)
line2D3.StartPoint = point2D3 'point de début
line2D3.EndPoint = point2D4 'point de fin

'Création des références pour faire les contraintes
Dim reference1 As Reference
Set reference1 = my_part.CreateReferenceFromObject(line_symetry) 'c'est la ligne de symétrie
Dim reference2 As Reference
Set reference2 = my_part.CreateReferenceFromObject(line2D2)
Dim reference3 As Reference
Set reference3 = my_part.CreateReferenceFromObject(line2D3)
Dim reference4 As Reference
Set reference4 = my_part.CreateReferenceFromObject(point2D1)
Dim reference5 As Reference
Set reference5 = my_part.CreateReferenceFromObject(point2D3)
Dim reference6 As Reference
Set reference6 = my_part.CreateReferenceFromObject(point2D4)
Dim reference7 As Reference
Set reference7 = my_part.CreateReferenceFromObject(point2D2)

'Contraintes:
Dim constraint3 As Constraint
Set constraint3 = constraints1.AddTriEltCst(catCstTypeSymmetry, reference3, reference2, reference1) 'symetrie entre les deux droites par rapport à la droite d'origine

Dim constraint4 As Constraint
Set constraint4 = constraints1.AddTriEltCst(catCstTypeSymmetry, reference4, reference5, reference1) 'symetrie entre deux points par rapport à la droite

Dim constraint5 As Constraint
Set constraint5 = constraints1.AddTriEltCst(catCstTypeSymmetry, reference6, reference7, reference1) 'symetrie entre deux points par rapport à la droite


'_________________________________Fin création droites structure chape_________________________________


'_________________________________Début génération de l'arrondi du bord de la chape_________________________________
'Déclaration variables utiles
Diam_tube = Fenetre_Selection.TextBox_diam_tube.Value
Diam_vis = Fenetre_Selection.TextBox_diam_vis.Value

'Création arrondis de la chape
Dim arrondi_chape_1 As Circle2D
Set arrondi_chape_1 = factory2D_extrusion.CreateCircle(0#, 0#, Diam_vis, 1, 2) 'creation du cercle
arrondi_chape_1.CenterPoint = centre_trou_2D 'centre
arrondi_chape_1.EndPoint = point2D2 'point 1
arrondi_chape_1.StartPoint = point2D4 'point 2

'Mise en place de la tangence avec une des droites structurantes
Dim reference8 As Reference
Set reference8 = my_part.CreateReferenceFromObject(arrondi_chape_1)
Dim constraint6 As Constraint
Set constraint6 = constraints1.AddBiEltCst(catCstTypeTangency, reference8, reference2)

'_________________________________Fin génération de l'arrondi du bord de la chape_________________________________

'_________________________________Début génération du segment fermant l'esquisse de la chape_________________________________

'Création droite de fermeture de l'esquisse de la chape
Dim fermeture_chape_1 As Line2D
Set fermeture_chape_1 = factory2D_extrusion.CreateLine(0#, 1#, 0#, -1#) 'creation ligne au hasard
fermeture_chape_1.StartPoint = point2D3 'point debut
fermeture_chape_1.EndPoint = point2D1 'point fin


'References pour contraindre la droite de fermeture de l'esquisse de la chape
Dim reference9 As Reference
Set reference9 = my_part.CreateReferenceFromObject(fermeture_chape_1)
Dim constraint7 As Constraint
Set constraint7 = constraints1.AddBiEltCst(catCstTypeDistance, reference9, ref_inter_axe_tube)

Dim position_bord_chape As Length
Set position_bord_chape = constraint7.Dimension
position_bord_chape.Value = 0# ' la chape est placée contre le tube

Dim constraint8 As Constraint
Set constraint8 = constraints1.AddMonoEltCst(catCstTypeLength, reference9) 'contrainte pour la largeur en bout de chape
constraint8.Mode = catCstModeDrivingDimension
Dim largeur_max_chape As Length
Set largeur_max_chape = constraint8.Dimension
largeur_max_chape.Value = Diam_tube

'_________________________________Fin génération du segment fermant l'esquisse de la chape_________________________________


'creation du trou de la chape
Dim trou_chape_1 As Circle2D
Set trou_chape_1 = factory2D_extrusion.CreateClosedCircle(0#, 0#, Diam_vis / 2)
trou_chape_1.CenterPoint = centre_trou_2D 'centre du cercle
Dim ref_trou_chape_1 As Reference
Set ref_trou_chape_1 = my_part.CreateReferenceFromObject(trou_chape_1)

'Contraintes complémentaires de l'esquisse (on veut qu'elle soit verte!)
Dim constraint9 As Constraint
Set constraint9 = constraints1.AddMonoEltCst(catCstTypeRadius, reference8) 'rayon du cercle
constraint9.Dimension.Value = Diam_vis

Dim constraint10 As Constraint
Set constraint10 = constraints1.AddMonoEltCst(catCstTypeRadius, ref_trou_chape_1) 'rayon du cercle
constraint10.Dimension.Value = (Diam_vis / 2)

mon_esquisse_chape.CloseEdition 'Sortie de l'esquisse

my_part.Update



'Travail dans le corps de pièce "Corps principal"
my_part.InWorkObject = my_body

'Extrusion de la chape
Dim ShapeFactory1 As ShapeFactory
Set ShapeFactory1 = my_part.ShapeFactory

epaisseur = Fenetre_Selection.TextBox_epaisseur.Value
Set ma_forme = ShapeFactory1.AddNewPad(mon_esquisse_chape, epaisseur)

my_part.Update

'Poche chape côté chassis
Set mon_esquisse_poche_1 = mes_esquisses.Add(Plan_normal_axe)
'Définition de l'objet de travail
my_part.InWorkObject = mon_esquisse_poche_1
'Edition de l'esquisse
Set factory2D_poche = mon_esquisse_poche_1.OpenEdition()

'Création du point d'intersection entre axe du tube et plan d'esquisse de la chape 1
Dim geometricElements1_2 As GeometricElements
Set geometricElements1_2 = mon_esquisse_chape.GeometricElements
Dim axis2D2 As Axis2D
Set axis2D2 = geometricElements1_2.Item("Repère")
Dim line2D1_2 As Line2D
Set line2D1_2 = axis2D1.GetItem("Axe horizontal")
Dim geometricElements2_2 As GeometricElements
Set geometricElements2_2 = factory2D_poche.CreateIntersections(Axe_Tube) 'La droite entre les deux points
Dim inter_axe_tube_2 As Geometry2D
Set inter_axe_tube_2 = geometricElements2_2.Item("Empreinte.1")
inter_axe_tube_2.Construction = True 'definir element de construction
Dim ref_inter_axe_tube_2 As Reference
Set ref_inter_axe_tube_2 = my_part.CreateReferenceFromObject(inter_axe_tube_2)
Dim point2D_axe As Point2D
Set point2D_axe = factory2D_poche.CreatePoint(0#, 0#)
Dim ref_point2D_axe As Reference
Set ref_point2D_axe = my_part.CreateReferenceFromObject(point2D_axe)

Dim constraints2 As Constraints
Set constraints2 = mon_esquisse_poche_1.Constraints
Dim coincidence As Constraint
Set coincidence = constraints2.AddBiEltCst(catCstTypeOn, ref_inter_axe_tube_2, ref_point2D_axe)



Dim poche_chape_1 As Circle2D
Set poche_chape_1 = factory2D_poche.CreateClosedCircle(0, 0, Diam_tube / 2)
poche_chape_1.CenterPoint = point2D_axe
Dim ref_poche_chape_1 As Reference
Set ref_poche_chape_1 = my_part.CreateReferenceFromObject(poche_chape_1)



Dim constraint11 As Constraint
Set constraint11 = constraints2.AddMonoEltCst(catCstTypeRadius, ref_poche_chape_1)
constraint11.Dimension.Value = Diam_tube / 2

'Sortie de l'esquisse
mon_esquisse_poche_1.CloseEdition

Dim pocket_poche_1 As Pocket
Set pocket_poche_1 = ShapeFactory1.AddNewPocket(mon_esquisse_poche_1, 1)

Dim limit_poche_1 As Limit
Set limit_poche_1 = pocket_poche_1.FirstLimit
limit_poche_1.LimitMode = catUpToLastLimit

my_part.Update

End Sub

Private Sub Image1_BeforeDragOver(ByVal Cancel As MSForms.ReturnBoolean, ByVal Data As MSForms.DataObject, ByVal X As Single, ByVal Y As Single, ByVal DragState As MSForms.fmDragState, ByVal Effect As MSForms.ReturnEffect, ByVal Shift As Integer)

End Sub

Attribute VB_Name = "Generation_chapes"
Sub CATMain()
'Creation de l'arborescence active
Set RootDoc = CATIA.ActiveDocument
Set RootProduct = RootDoc.Product
Set AllProds = RootProduct.Products

'Création de deux parts dans l'arborescence active
Set Mon_Prod1 = AllProds.AddNewComponent("Part", "") 'part dans laquelle sera dessinée la chape 1
Set Mon_Prod2 = AllProds.AddNewComponent("Part", "") 'part dans laquelle sera dessinée la chape 2
Set AllDocs = CATIA.Documents
Set Docpart1 = AllDocs.Item(Mon_Prod1.PartNumber + ".CATPart") 'Remplacer Mon_Prod.PartNumber + ".CATPart" par Ma_piece.CATPart
Set Docpart2 = AllDocs.Item(Mon_Prod2.PartNumber + ".CATPart") 'Remplacer Mon_Prod.PartNumber + ".CATPart" par Ma_piece.CATPart
Set part_chape_1 = Docpart1.Part
Set part_chape_2 = Docpart2.Part

Set HSF1 = part_chape_1.HybridShapeFactory
Set HSF2 = part_chape_2.HybridShapeFactory

'Récupère HybridBodies collection dans Part Document
Set Listbodies1 = part_chape_1.Bodies
Set Listbodies2 = part_chape_2.Bodies

'Crée le corps de travail et le défini comme corps de travail de la part créée
Set B1 = Listbodies1.Item("Corps principal")
part_chape_1.InWorkObject = B1

Set B2 = Listbodies2.Item("Corps principal")
part_chape_2.InWorkObject = B2


'Lancement fenetre de selection des données
Fenetre_Selection.Show Modal

End Sub

Attribute VB_Name = "Module_variables"
' ----------------------------------------------------------
' Création des variables globales communes aux deux chapes
' ----------------------------------------------------------
Public RootDoc As Document
Public RootProduct As Product
Public AllProds As Products
Public Mon_Prod As Product
Public AllDocs As Documents
Public Docpart1 As PartDocument

Public Plan_normal_axe As HybridShapePlaneNormal
Public Axe_Rotule As HybridShapeLinePtPt
Public Diam_tube As Long
Public Diam_vis As Long
Public epaisseur As Long

' ----------------------------------------
' Création des variables globales chape 1
' ----------------------------------------
Public HSF1 As HybridShapeFactory
Public Listbodies1 As Bodies
Public B1 As Body
Public part_chape_1 As Part


Public Pt_debut_1 As HybridShapePointCoord
Public Pt_fin_1 As HybridShapePointCoord
Public pt1_chape_1 As HybridShapePointCoord
Public pt2_chape_1 As HybridShapePointCoord
Public Plan_chape_1 As HybridShapePlaneNormal


' ----------------------------------------
' Création des variables globales chape 2
' ----------------------------------------
Public HSF2 As HybridShapeFactory
Public Listbodies2 As Bodies
Public B2 As Body
Public part_chape_2 As Part

Public Pt_debut_2 As HybridShapePointCoord
Public Pt_fin_2 As HybridShapePointCoord
Public pt1_chape_2 As HybridShapePointCoord
Public pt2_chape_2 As HybridShapePointCoord
Public Plan_chape_2 As HybridShapePlaneNormal
